Attribute VB_Name = "M_0"
Public Sub showFormPerfisul01()
    formPerfisul01.Show
End Sub

Attribute VB_Name = "M_CircleAligner"
' BricsCAD VBA Macro: Align Larger Circles to Smaller Circle Centers
' Iterates all circles in the active document, finds larger circles whose centers are inside smaller circles, and moves them to the smaller circle's center

Public Sub CircleAligner()
    Dim doc As AcadDocument
    Set doc = ThisDrawing
    
    Dim circles As collection
    Set circles = New collection
    
    Dim ent As AcadEntity
    ' Collect all circles in the drawing
    For Each ent In doc.modelSpace
        If ent.ObjectName = "AcDbCircle" Then
            circles.Add ent
        End If
    Next
    
    Dim i As Integer, j As Integer
    Dim c1 As AcadCircle, c2 As AcadCircle
    
    ' Iterate through all pairs of circles
    For i = 1 To circles.count
        Set c1 = circles(i)
        For j = 1 To circles.count
            If i <> j Then
                Set c2 = circles(j)
                ' Check if c2 center is inside c1 and c2 has bigger radius
                If c2.radius > c1.radius Then
                    If IsPointInsideCircle(c1, c2.center) Then
                        ' Move c2 to c1's center
                        c2.center = c1.center
                    End If
                End If
            End If
        Next j
    Next i
    
    doc.Regen acAllViewports
End Sub

' Helper function: checks if a point is inside a circle
Function IsPointInsideCircle(circ As AcadCircle, pt As Variant) As Boolean
    Dim dx As Double, dy As Double, dz As Double
    dx = pt(0) - circ.center(0)
    dy = pt(1) - circ.center(1)
    dz = pt(2) - circ.center(2)
    IsPointInsideCircle = Sqr(dx * dx + dy * dy + dz * dz) < circ.radius
End Function

Attribute VB_Name = "M_CodeFixer"
Option Explicit

Public Sub FixDuplicatedCodes()
    Dim acadDoc As Object ' AcadDocument
    Dim modelSpace As Object ' AcadModelSpace
    Dim entity As Object ' AcadEntity
    Dim textObj As Object ' AcadText
    Dim layerName As String
    Dim ignoreValue As String
    Dim textObjects As collection
    Dim textData() As Variant
    Dim i As Long, j As Long
    Dim temp As Variant
    Dim dict As Object
    Dim txt As String
    Dim changedCount As Long
    Dim suffix As String

    ' 1. Get layer and ignore value from form
    On Error Resume Next
    layerName = formPerfisul01.cbCamada01.Value
    ignoreValue = formPerfisul01.cbTexto01.Value
    If Err.Number <> 0 Or layerName = "" Or layerName = "-- Selecione uma camada --" Then
        MsgBox "Selecione uma camada válida no formulário.", vbExclamation
        Exit Sub
    End If
    On Error GoTo 0

    Set acadDoc = ThisDrawing
    Set modelSpace = acadDoc.modelSpace
    Set textObjects = New collection

    ' 2. Collect all text objects in the layer except those to ignore
    For Each entity In modelSpace
        If entity.layer = layerName Then
            If TypeOf entity Is AcadText Then
                If entity.TextString <> ignoreValue Then
                    textObjects.Add entity
                End If
            End If
        End If
    Next entity

    If textObjects.count = 0 Then
        MsgBox "Nenhum texto encontrado na camada selecionada.", vbInformation
        Exit Sub
    End If

    ' 3. Store text and reference for sorting
    ReDim textData(1 To textObjects.count, 1 To 2)
    For i = 1 To textObjects.count
        Set textObj = textObjects(i)
        textData(i, 1) = textObj.TextString
        Set textData(i, 2) = textObj
    Next i

    ' 4. Sort textData alphabetically by text string (simple bubble sort)
    For i = 1 To UBound(textData, 1) - 1
        For j = i + 1 To UBound(textData, 1)
            If StrComp(textData(i, 1), textData(j, 1), vbTextCompare) > 0 Then
                temp = textData(i, 1): textData(i, 1) = textData(j, 1): textData(j, 1) = temp
                Set temp = textData(i, 2): Set textData(i, 2) = textData(j, 2): Set textData(j, 2) = temp
            End If
        Next j
    Next i

    ' 5. First pass: count occurrences of each text
    Set dict = CreateObject("Scripting.Dictionary")
    For i = 1 To UBound(textData, 1)
        txt = textData(i, 1)
        If dict.Exists(txt) Then
            dict(txt) = dict(txt) + 1
        Else
            dict(txt) = 1
        End If
    Next i
    
    ' 6. Second pass: add suffixes to duplicated texts
    Dim currentCount As Object
    Set currentCount = CreateObject("Scripting.Dictionary")
    changedCount = 0

    For i = 1 To UBound(textData, 1)
        Set textObj = textData(i, 2)
        txt = textData(i, 1)
        
        If dict(txt) > 1 Then
            ' This text has duplicates, add suffix
            If currentCount.Exists(txt) Then
                currentCount(txt) = currentCount(txt) + 1
            Else
                currentCount(txt) = 1
            End If
            suffix = Right("0" & CStr(currentCount(txt)), 2) ' Format as 01, 02, etc.
            textObj.TextString = txt & suffix
            textObj.Update
            changedCount = changedCount + 1
        End If
    Next i

    acadDoc.Regen acAllViewports

    ' Display result message
    MsgBox "Correção de códigos duplicados concluída." & vbCrLf & _
           "Quantidade de valores alterados: " & changedCount, vbInformation
End Sub

Attribute VB_Name = "M_FixSmallGaps"
Public Sub FixSmallGaps()
    ' Procedure to find and fix small gaps between drawing elements
    ' Author: Created for BricsCAD VBA
    ' Date: August 2025
    
    Dim doc As AcadDocument
    Dim modelSpace As AcadModelSpace
    Dim entity As AcadEntity
    Dim i As Integer, j As Integer
    Dim minGap As Double, maxGap As Double
    Dim minGapMm As Double, maxGapMm As Double
    Dim response As String
    Dim userResponse As VbMsgBoxResult
    Dim unitFactor As Double
    Dim connectingLinesCount As Integer
    Dim locatorCirclesCount As Integer
    Dim addLocatorCircles As Boolean
    Dim locatorCircleRadius As Double
    
    ' Initialize counters
    connectingLinesCount = 0
    locatorCirclesCount = 0
    
    ' Initialize document and model space
    Set doc = ThisDrawing
    Set modelSpace = doc.modelSpace
    
    ' Get gap values from user (in mm)
    response = InputBox("Enter minimum gap value in mm:", "Minimum Gap", "0.00001")
    If response = "" Then Exit Sub
    ' Handle decimal separator issues (replace comma with period if needed)
    response = Replace(response, ",", ".")
    minGapMm = val(response)
    ' MsgBox "Debug: minGapMm = " & minGapMm, vbInformation ' Debug line
    
    response = InputBox("Enter maximum gap value in mm:", "Maximum Gap", "0.05")
    If response = "" Then Exit Sub
    ' Handle decimal separator issues (replace comma with period if needed)
    response = Replace(response, ",", ".")
    maxGapMm = val(response)
    ' MsgBox "Debug: maxGapMm = " & maxGapMm, vbInformation ' Debug line
    
    ' Convert from mm to drawing units
    ' Ask user about drawing units to ensure correct conversion
    Dim unitsResponse As String
    unitsResponse = InputBox("What are your drawing units?" & vbCrLf & _
                           "Enter 'mm' for millimeters" & vbCrLf & _
                           "Enter 'm' for meters" & vbCrLf & _
                           "Enter 'in' for inches", _
                           "Drawing Units", "mm")
    If unitsResponse = "" Then Exit Sub
    
    Select Case LCase(unitsResponse)
        Case "mm"
            unitFactor = 1 ' No conversion needed
        Case "m"
            unitFactor = 0.001 ' Convert mm to meters
        Case "in"
            unitFactor = 1 / 25.4 ' Convert mm to inches
        Case Else
            MsgBox "Invalid unit. Assuming meters.", vbExclamation
            unitFactor = 0.001
    End Select
    
    minGap = minGapMm * unitFactor
    maxGap = maxGapMm * unitFactor
    locatorCircleRadius = (5# / 2#) * unitFactor ' 5 mm diameter circle => 2.5 mm radius
    
    ' Debug info
    MsgBox "Converting " & minGapMm & "-" & maxGapMm & " mm to " & Format(minGap, "0.000000") & "-" & Format(maxGap, "0.000000") & " drawing units", vbInformation
    
    ' Validate input
    If minGap >= maxGap Then
        MsgBox "Minimum gap must be less than maximum gap!", vbExclamation
        Exit Sub
    End If
    
    ' Create collections to store line/arc/curve entities and their endpoints
    Dim entities As New collection
    Dim endpoints As New collection
    Dim entityTypes As New collection
    
    ' Collect all lines, arcs, and curves with their endpoints
    ' MsgBox "Analyzing drawing elements...", vbInformation
    
    For i = 0 To modelSpace.count - 1
        Set entity = modelSpace.item(i)
        
        Select Case entity.ObjectName
            Case "AcDbLine"
                Dim line As AcadLine
                Set line = entity
                entities.Add line
                endpoints.Add Array(line.startPoint, line.endPoint)
                entityTypes.Add "Line"
                
            Case "AcDbArc"
                Dim arc As AcadArc
                Set arc = entity
                entities.Add arc
                ' Calculate arc endpoints from center, radius, and angles with high precision
                Dim arcStartPt(2) As Double, arcEndPt(2) As Double
                arcStartPt(0) = arc.center(0) + arc.radius * Cos(arc.startAngle)
                arcStartPt(1) = arc.center(1) + arc.radius * Sin(arc.startAngle)
                arcStartPt(2) = arc.center(2)
                arcEndPt(0) = arc.center(0) + arc.radius * Cos(arc.endAngle)
                arcEndPt(1) = arc.center(1) + arc.radius * Sin(arc.endAngle)
                arcEndPt(2) = arc.center(2)
                endpoints.Add Array(arcStartPt, arcEndPt)
                entityTypes.Add "Arc"
                
            Case "AcDbPolyline"
                Dim pline As AcadLWPolyline
                Set pline = entity
                entities.Add pline
                ' Get all coordinates and extract first and last points
                Dim coords As Variant
                coords = pline.Coordinates
                Dim StartPt(2) As Double, EndPt(2) As Double
                ' First vertex (coordinates are stored as X1,Y1,X2,Y2,...)
                StartPt(0) = coords(0): StartPt(1) = coords(1): StartPt(2) = 0
                ' Last vertex
                Dim lastIndex As Integer
                lastIndex = UBound(coords) - 1
                EndPt(0) = coords(lastIndex - 1): EndPt(1) = coords(lastIndex): EndPt(2) = 0
                endpoints.Add Array(StartPt, EndPt)
                entityTypes.Add "Polyline"
                
            Case "AcDbSpline"
                Dim spline As AcadSpline
                Set spline = entity
                entities.Add spline
                ' Safely attempt to read start/end points; some spline objects may not expose these properties
                On Error Resume Next
                Dim sStart As Variant, sEnd As Variant
                sStart = spline.startPoint
                sEnd = spline.endPoint
                If Err.Number <> 0 Then
                    Err.Clear
                    Dim bbMin(2) As Double, bbMax(2) As Double
                    ' Fall back to bounding box corners if StartPoint/EndPoint are not available
                    spline.GetBoundingBox bbMin, bbMax
                    sStart = bbMin
                    sEnd = bbMax
                End If
                On Error GoTo 0
                endpoints.Add Array(sStart, sEnd)
                entityTypes.Add "Spline"
        End Select
    Next i
    
    If entities.count = 0 Then
        MsgBox "No lines, arcs, or curves found in the drawing.", vbInformation
        Exit Sub
    End If
    
    ' Ask user if they want to decide on each gap individually or fix all automatically
    Dim fixModeResponse As VbMsgBoxResult
    fixModeResponse = MsgBox("How would you like to handle gaps?" & vbCrLf & vbCrLf & _
                           "Yes - Ask me about each gap individually" & vbCrLf & _
                           "No - Fix all gaps automatically" & vbCrLf & _
                           "Cancel - Exit without fixing", _
                           vbYesNoCancel + vbQuestion, "Gap Fixing Mode")
    
    If fixModeResponse = vbCancel Then Exit Sub
    
    Dim autoFixMode As Boolean
    autoFixMode = (fixModeResponse = vbNo)

    ' Ask if locator circles should be added before fixing each found gap
    Dim locatorResponse As VbMsgBoxResult
    locatorResponse = MsgBox("Add a 5 mm red locator circle at each found gap before fixing?", _
                            vbYesNoCancel + vbQuestion, "Locator Circles")
    If locatorResponse = vbCancel Then Exit Sub
    addLocatorCircles = (locatorResponse = vbYes)
    
    ' Search for gaps between endpoints
    Dim gapsFound As Integer
    gapsFound = 0
    
    ' Debug/count info (suppress in auto-fix mode as per new requirement)
    If Not autoFixMode Then
        MsgBox "Found " & entities.count & " entities to analyze for gaps.", vbInformation
    End If
    
    For i = 1 To entities.count
        For j = i + 1 To entities.count
            ' Get endpoints for both entities
            Dim endpoints1 As Variant, endpoints2 As Variant
            endpoints1 = endpoints(i)
            endpoints2 = endpoints(j)
            
            ' Check all combinations of endpoints
            Dim combinations(3) As Variant
            combinations(0) = Array(endpoints1(0), endpoints2(0)) ' Start1 to Start2
            combinations(1) = Array(endpoints1(0), endpoints2(1)) ' Start1 to End2
            combinations(2) = Array(endpoints1(1), endpoints2(0)) ' End1 to Start2
            combinations(3) = Array(endpoints1(1), endpoints2(1)) ' End1 to End2
            
            Dim k As Integer
            For k = 0 To 3
                Dim point1 As Variant, point2 As Variant
                point1 = combinations(k)(0)
                point2 = combinations(k)(1)
                
                ' Calculate distance between points
                Dim distance As Double
                distance = Sqr((point2(0) - point1(0)) ^ 2 + (point2(1) - point1(1)) ^ 2 + (point2(2) - point1(2)) ^ 2)
                
                ' Skip if points are the same (distance = 0) to avoid connecting endpoints of the same entity
                If distance < 0.0000001 Then GoTo NextCombination
                
                ' Check if distance is within gap range
                If distance >= minGap And distance <= maxGap Then
                    gapsFound = gapsFound + 1

                    ' Add optional locator circle centered on the gap midpoint before any fix action
                    If addLocatorCircles Then
                        Dim gapCenter(2) As Double
                        Dim locatorCircle As AcadCircle
                        gapCenter(0) = (point1(0) + point2(0)) / 2
                        gapCenter(1) = (point1(1) + point2(1)) / 2
                        gapCenter(2) = (point1(2) + point2(2)) / 2
                        Set locatorCircle = modelSpace.AddCircle(gapCenter, locatorCircleRadius)
                        locatorCircle.Color = acRed
                        locatorCirclesCount = locatorCirclesCount + 1
                    End If
                    
                    ' Determine which endpoints are involved
                    Dim endpointDesc As String
                    Select Case k
                        Case 0: endpointDesc = "Start to Start"
                        Case 1: endpointDesc = "Start to End"
                        Case 2: endpointDesc = "End to Start"
                        Case 3: endpointDesc = "End to End"
                    End Select
                    
                    Dim shouldFixGap As Boolean
                    shouldFixGap = False
                    
                    ' Declare displayDistance once for both branches
                    Dim displayDistance As Double
                    displayDistance = distance / unitFactor
                    
                    If autoFixMode Then
                        ' In automatic mode, fix all gaps silently (no per-gap MsgBoxes)
                        shouldFixGap = True
                        ' Optional: still zoom to the gap for visual feedback; comment out next line to disable zoom during auto mode
                        Call ZoomToGap(point1, point2, distance * 10)
                    Else
                        ' In manual mode, ask user about each gap
                        Call ZoomToGap(point1, point2, distance * 10) ' Zoom with 10x buffer
                        
                        ' Ask user if they want to fix this gap
                        userResponse = MsgBox("Gap found between " & entityTypes(i) & " and " & entityTypes(j) & vbCrLf & _
                                            "Connection: " & endpointDesc & vbCrLf & _
                                            "Distance: " & Format(displayDistance, "0.000") & " mm" & vbCrLf & _
                                            "Raw distance: " & Format(distance, "0.000000") & " drawing units" & vbCrLf & _
                                            "Point 1: (" & Format(point1(0), "0.000") & ", " & Format(point1(1), "0.000") & ")" & vbCrLf & _
                                            "Point 2: (" & Format(point2(0), "0.000") & ", " & Format(point2(1), "0.000") & ")" & vbCrLf & _
                                            "Do you want to fix this gap?", vbYesNoCancel + vbQuestion, "Fix Gap?")
                        
                        If userResponse = vbCancel Then
                            Exit Sub
                        ElseIf userResponse = vbYes Then
                            shouldFixGap = True
                        End If
                    End If
                    
                    ' Fix the gap if requested
                    If shouldFixGap Then
                        ' Try to fix by moving endpoints first
                        Dim fixedByMoving As Boolean
                        fixedByMoving = False
                        
                        ' Check if both entities can be modified by moving endpoints
                        If CanMoveEndpoint(entities(i)) And CanMoveEndpoint(entities(j)) Then
                            ' Calculate middle point
                            Dim midPoint(2) As Double
                            midPoint(0) = (point1(0) + point2(0)) / 2
                            midPoint(1) = (point1(1) + point2(1)) / 2
                            midPoint(2) = (point1(2) + point2(2)) / 2
                            
                        ' Try to move endpoints to middle point
                        Dim moved1 As Boolean, moved2 As Boolean
                        Dim newSpline1 As AcadSpline, newSpline2 As AcadSpline
                        Set newSpline1 = Nothing
                        Set newSpline2 = Nothing
                        
                        ' Handle potential arc-to-spline conversion for first entity
                        If entities(i).ObjectName = "AcDbArc" Then
                            moved1 = MoveEndpointWithConversion(entities(i), point1, midPoint, k, True, newSpline1)
                            If moved1 And Not newSpline1 Is Nothing Then
                                ' Note: Collection updates will be handled after both conversions
                                ' to avoid index invalidation during the loop
                            End If
                        Else
                            moved1 = MoveEndpoint(entities(i), point1, midPoint, k, True)
                        End If
                        
                        ' Handle potential arc-to-spline conversion for second entity
                        If entities(j).ObjectName = "AcDbArc" Then
                            moved2 = MoveEndpointWithConversion(entities(j), point2, midPoint, k, False, newSpline2)
                            If moved2 And Not newSpline2 Is Nothing Then
                                ' Note: Collection updates will be handled after both conversions
                                ' to avoid index invalidation during the loop
                            End If
                        Else
                            moved2 = MoveEndpoint(entities(j), point2, midPoint, k, False)
                        End If
                        
                        ' Now safely update collections after both conversions are complete
                        ' Handle first entity replacement (do j first since j > i, to preserve i's index)
                        If moved2 And Not newSpline2 Is Nothing Then
                            On Error Resume Next
                            Dim spline2Start As Variant, spline2End As Variant
                            spline2Start = newSpline2.startPoint
                            spline2End = newSpline2.endPoint
                            On Error GoTo 0
                            
                            If Not IsEmpty(spline2Start) And Not IsEmpty(spline2End) Then
                                entities.Remove j
                                entityTypes.Remove j
                                endpoints.Remove j
                                ' Add back at the same logical position, but safely handle bounds
                                If j <= entities.count Then
                                    entities.Add newSpline2, , j
                                    entityTypes.Add "Spline", , j
                                    endpoints.Add Array(spline2Start, spline2End), , j
                                Else
                                    ' Add at end if original position is now out of bounds
                                    entities.Add newSpline2
                                    entityTypes.Add "Spline"
                                    endpoints.Add Array(spline2Start, spline2End)
                                End If
                            End If
                        End If
                        
                        ' Handle second entity replacement (i is still valid since we processed j first)
                        If moved1 And Not newSpline1 Is Nothing Then
                            On Error Resume Next
                            Dim spline1Start As Variant, spline1End As Variant
                            spline1Start = newSpline1.startPoint
                            spline1End = newSpline1.endPoint
                            On Error GoTo 0
                            
                            If Not IsEmpty(spline1Start) And Not IsEmpty(spline1End) Then
                                entities.Remove i
                                entityTypes.Remove i
                                endpoints.Remove i
                                ' Add back at the same logical position, but safely handle bounds
                                If i <= entities.count Then
                                    entities.Add newSpline1, , i
                                    entityTypes.Add "Spline", , i
                                    endpoints.Add Array(spline1Start, spline1End), , i
                                Else
                                    ' Add at end if original position is now out of bounds
                                    entities.Add newSpline1
                                    entityTypes.Add "Spline"
                                    endpoints.Add Array(spline1Start, spline1End)
                                End If
                            End If
                        End If
                        
                        fixedByMoving = moved1 And moved2
                        End If
                        
                        ' If couldn't fix by moving endpoints, create a connecting line
                        If Not fixedByMoving Then
                            Dim connectingLine As AcadLine
                            Set connectingLine = modelSpace.AddLine(point1, point2)
                            connectingLine.Color = acRed ' Make it red to highlight the fix
                            connectingLine.Linetype = "CONTINUOUS" ' Ensure it's visible
                            connectingLinesCount = connectingLinesCount + 1
                            
                            If Not autoFixMode Then
                                MsgBox "Gap filled with connecting line (entities too complex to modify)!" & vbCrLf & _
                                       "Line color: Red for easy identification", vbInformation
                            End If
                        Else
                            If Not autoFixMode Then
                                MsgBox "Gap fixed by moving endpoints!", vbInformation
                            End If
                        End If
                        
                        ' Regenerate the drawing
                        doc.Regen acActiveViewport
                    End If
                End If
NextCombination:
            Next k
        Next j
    Next i
    
    ' Zoom extents when done
    doc.Application.ZoomExtents
    
    If gapsFound = 0 Then
        MsgBox "No gaps found within the specified range (" & minGapMm & " to " & maxGapMm & " mm).", vbInformation
    Else
        Dim fixSummary As String
        fixSummary = "Gap analysis complete. " & gapsFound & " gaps were found"
        If addLocatorCircles Then
            fixSummary = fixSummary & vbCrLf & locatorCirclesCount & " red locator circles were added"
        End If
        If connectingLinesCount > 0 Then
            fixSummary = fixSummary & vbCrLf & connectingLinesCount & " gaps were filled with red connecting lines"
            fixSummary = fixSummary & vbCrLf & (gapsFound - connectingLinesCount) & " gaps were fixed by moving endpoints"
        Else
            fixSummary = fixSummary & vbCrLf & "All gaps were fixed by moving endpoints"
        End If
        
        If autoFixMode Then
            fixSummary = fixSummary & " automatically."
        Else
            fixSummary = fixSummary & "."
        End If
        
        MsgBox fixSummary, vbInformation
    End If
    
End Sub

Private Function CanMoveEndpoint(entity As AcadEntity) As Boolean
    ' Check if an entity's endpoint can be safely moved
    
    Select Case entity.ObjectName
        Case "AcDbLine"
            CanMoveEndpoint = True ' Lines can always be moved
        Case "AcDbArc"
            CanMoveEndpoint = True ' Arcs can be modified (though complex, will check angle change in ModifyArcEndpoint)
        Case "AcDbPolyline"
            CanMoveEndpoint = True ' Polylines can be modified
        Case "AcDbSpline"
            CanMoveEndpoint = False ' Splines are too complex
        Case "AcDbCircle"
            CanMoveEndpoint = False ' Circles don't have endpoints
        Case "AcDbEllipse"
            CanMoveEndpoint = False ' Ellipses are complex
        Case Else
            CanMoveEndpoint = False ' Unknown entities default to false for safety
    End Select
End Function

Private Sub ZoomToGap(point1 As Variant, point2 As Variant, bufferDistance As Double)
    ' Zoom to the gap region with a buffer
    Dim doc As AcadDocument
    Set doc = ThisDrawing
    
    ' Calculate zoom window
    Dim minX As Double, minY As Double, maxX As Double, maxY As Double
    
    minX = IIf(point1(0) < point2(0), point1(0), point2(0)) - bufferDistance
    maxX = IIf(point1(0) > point2(0), point1(0), point2(0)) + bufferDistance
    minY = IIf(point1(1) < point2(1), point1(1), point2(1)) - bufferDistance
    maxY = IIf(point1(1) > point2(1), point1(1), point2(1)) + bufferDistance
    
    ' Create zoom window points
    Dim lowerLeft(2) As Double, upperRight(2) As Double
    lowerLeft(0) = minX: lowerLeft(1) = minY: lowerLeft(2) = 0
    upperRight(0) = maxX: upperRight(1) = maxY: upperRight(2) = 0
    
    ' Zoom to window
    doc.Application.ZoomWindow lowerLeft, upperRight
End Sub

Private Function MoveEndpointWithConversion(entity As AcadEntity, oldPoint As Variant, newPoint As Variant, combinationIndex As Integer, isFirstEntity As Boolean, ByRef newSpline As AcadSpline) As Boolean
    ' Move endpoint with potential arc-to-spline conversion
    ' Returns the new spline via ByRef if conversion occurs
    
    On Error GoTo ErrorHandler
    
    If entity.ObjectName = "AcDbArc" Then
        Dim arc As AcadArc
        Set arc = entity
        MoveEndpointWithConversion = ModifyArcEndpoint(arc, oldPoint, newPoint, combinationIndex, isFirstEntity, newSpline)
    Else
        ' For non-arc entities, use regular move endpoint
        MoveEndpointWithConversion = MoveEndpoint(entity, oldPoint, newPoint, combinationIndex, isFirstEntity)
    End If
    
    Exit Function
    
ErrorHandler:
    MoveEndpointWithConversion = False
End Function

Private Function MoveEndpoint(entity As AcadEntity, oldPoint As Variant, newPoint As Variant, combinationIndex As Integer, isFirstEntity As Boolean) As Boolean
    ' Move the endpoint of an entity to a new position
    ' Returns True if successful, False if failed
    
    On Error GoTo ErrorHandler
    
    Select Case entity.ObjectName
        Case "AcDbLine"
            Dim line As AcadLine
            Set line = entity
            
            ' Determine which endpoint to move by checking which is closer to oldPoint
            Dim distToStart As Double, distToEnd As Double
            distToStart = Sqr((oldPoint(0) - line.startPoint(0)) ^ 2 + (oldPoint(1) - line.startPoint(1)) ^ 2)
            distToEnd = Sqr((oldPoint(0) - line.endPoint(0)) ^ 2 + (oldPoint(1) - line.endPoint(1)) ^ 2)
            
            If distToStart < distToEnd Then
                line.startPoint = newPoint
            Else
                line.endPoint = newPoint
            End If
            MoveEndpoint = True
            
        Case "AcDbArc"
            ' Arcs cannot be modified directly in this function
            ' Return False to use connecting line instead
            MoveEndpoint = False
            
        Case "AcDbPolyline"
            Dim pline As AcadLWPolyline
            Set pline = entity
            
            ' Get current start and end points
            Dim coords As Variant
            coords = pline.Coordinates
            Dim StartPt(2) As Double, EndPt(2) As Double
            StartPt(0) = coords(0): StartPt(1) = coords(1): StartPt(2) = 0
            Dim lastIndex As Integer
            lastIndex = UBound(coords) - 1
            EndPt(0) = coords(lastIndex - 1): EndPt(1) = coords(lastIndex): EndPt(2) = 0
            
            ' Determine which endpoint to move
            Dim distToStartPL As Double, distToEndPL As Double
            distToStartPL = Sqr((oldPoint(0) - StartPt(0)) ^ 2 + (oldPoint(1) - StartPt(1)) ^ 2)
            distToEndPL = Sqr((oldPoint(0) - EndPt(0)) ^ 2 + (oldPoint(1) - EndPt(1)) ^ 2)
            
            If distToStartPL < distToEndPL Then
                ' Move start point
                Dim startCoord As Variant
                startCoord = pline.Coordinate(0)
                startCoord(0) = newPoint(0)
                startCoord(1) = newPoint(1)
                pline.Coordinate(0) = startCoord
            Else
                ' Move end point
                Dim endCoord As Variant
                Dim lastIdx As Integer
                lastIdx = pline.NumberOfVertices - 1
                endCoord = pline.Coordinate(lastIdx)
                endCoord(0) = newPoint(0)
                endCoord(1) = newPoint(1)
                pline.Coordinate(lastIdx) = endCoord
            End If
            MoveEndpoint = True
            
        Case "AcDbSpline"
            ' Splines are too complex to modify safely
            MoveEndpoint = False
            
        Case Else
            ' Unknown entity type
            MoveEndpoint = False
            
    End Select
    Exit Function
    
ErrorHandler:
    MoveEndpoint = False
End Function

Private Function ModifyArcEndpoint(arc As AcadArc, oldPoint As Variant, newPoint As Variant, combinationIndex As Integer, isFirstEntity As Boolean, ByRef newSpline As AcadSpline) As Boolean
    ' Convert arc to spline and modify endpoint for more reliable gap fixing
    ' This approach provides better flexibility than trying to modify arc geometry
    ' Returns the new spline via ByRef parameter if conversion occurs
    
    On Error GoTo ErrorHandler
    
    ' Calculate gap size to determine if we should modify the arc
    Dim gapSize As Double
    gapSize = Sqr((newPoint(0) - oldPoint(0)) ^ 2 + (newPoint(1) - oldPoint(1)) ^ 2)
    
    ' Only modify arc for reasonable gaps (less than 50% of radius)
    If gapSize >= arc.radius * 0.5 Then
        ' Large gap: don't modify arc, use connecting line instead
        ModifyArcEndpoint = False
        Exit Function
    End If
    
    ' Convert arc to spline and modify the endpoint
    ModifyArcEndpoint = ConvertArcToSplineAndModify(arc, oldPoint, newPoint, newSpline)
    
    Exit Function
    
ErrorHandler:
    ModifyArcEndpoint = False
End Function

Private Function ConvertArcToSplineAndModify(arc As AcadArc, oldPoint As Variant, newPoint As Variant, ByRef newSpline As AcadSpline) As Boolean
    ' Convert arc to spline, modify endpoint, and replace the original arc
    ' Returns the new spline via ByRef parameter
    
    On Error GoTo ErrorHandler
    
    Dim doc As AcadDocument
    Dim modelSpace As AcadModelSpace
    Set doc = ThisDrawing
    Set modelSpace = doc.modelSpace
    
    ' Get arc properties
    Dim center As Variant, radius As Double
    Dim startAngle As Double, endAngle As Double
    center = arc.center
    radius = arc.radius
    startAngle = arc.startAngle
    endAngle = arc.endAngle
    
    ' Calculate current endpoints
    Dim currentStartPt(2) As Double, currentEndPt(2) As Double
    currentStartPt(0) = center(0) + radius * Cos(startAngle)
    currentStartPt(1) = center(1) + radius * Sin(startAngle)
    currentStartPt(2) = center(2)
    currentEndPt(0) = center(0) + radius * Cos(endAngle)
    currentEndPt(1) = center(1) + radius * Sin(endAngle)
    currentEndPt(2) = center(2)
    
    ' Determine which endpoint to modify
    Dim distToStart As Double, distToEnd As Double
    distToStart = Sqr((oldPoint(0) - currentStartPt(0)) ^ 2 + (oldPoint(1) - currentStartPt(1)) ^ 2)
    distToEnd = Sqr((oldPoint(0) - currentEndPt(0)) ^ 2 + (oldPoint(1) - currentEndPt(1)) ^ 2)
    
    ' Generate control points for the spline based on the arc
    Dim numPoints As Integer
    numPoints = 7 ' Use 7 points for smooth curve approximation
    
    Dim splinePoints() As Double
    ReDim splinePoints((numPoints * 3) - 1) ' 3 coordinates per point
    
    ' Calculate the angular span of the arc
    Dim totalAngle As Double
    totalAngle = endAngle - startAngle
    
    ' Handle angle wrapping for arcs that cross 0 degrees
    If totalAngle < 0 Then
        totalAngle = totalAngle + 2 * 3.14159265358979 ' Add 2*PI
    End If
    
    ' Generate points along the arc curve
    Dim i As Integer
    For i = 0 To numPoints - 1
        Dim currentAngle As Double
        If i = 0 Then
            ' First point - use modified start or original start
            If distToStart < distToEnd Then
                ' Modifying start point
                splinePoints(i * 3) = newPoint(0)
                splinePoints(i * 3 + 1) = newPoint(1)
                splinePoints(i * 3 + 2) = newPoint(2)
            Else
                ' Original start point
                splinePoints(i * 3) = currentStartPt(0)
                splinePoints(i * 3 + 1) = currentStartPt(1)
                splinePoints(i * 3 + 2) = currentStartPt(2)
            End If
        ElseIf i = numPoints - 1 Then
            ' Last point - use modified end or original end
            If distToStart >= distToEnd Then
                ' Modifying end point
                splinePoints(i * 3) = newPoint(0)
                splinePoints(i * 3 + 1) = newPoint(1)
                splinePoints(i * 3 + 2) = newPoint(2)
            Else
                ' Original end point
                splinePoints(i * 3) = currentEndPt(0)
                splinePoints(i * 3 + 1) = currentEndPt(1)
                splinePoints(i * 3 + 2) = currentEndPt(2)
            End If
        Else
            ' Intermediate points - calculate along arc
            Dim t As Double
            t = CDbl(i) / CDbl(numPoints - 1)
            currentAngle = startAngle + t * totalAngle
            
            splinePoints(i * 3) = center(0) + radius * Cos(currentAngle)
            splinePoints(i * 3 + 1) = center(1) + radius * Sin(currentAngle)
            splinePoints(i * 3 + 2) = center(2)
        End If
    Next i
    
    ' Create the spline
    Set newSpline = modelSpace.AddSpline(splinePoints, Empty, Empty)
    
    ' Copy properties from original arc
    newSpline.Color = arc.Color
    newSpline.layer = arc.layer
    newSpline.Linetype = arc.Linetype
    newSpline.LinetypeScale = arc.LinetypeScale
    newSpline.Lineweight = arc.Lineweight
    
    ' Delete the original arc
    arc.Delete
    
    ConvertArcToSplineAndModify = True
    Exit Function
    
ErrorHandler:
    ConvertArcToSplineAndModify = False
End Function

Private Sub UpdateEntityEndpoints(entity As AcadEntity, endpoints As collection, entityIndex As Integer)
    ' Update the endpoint information in the collection after entity modification
    ' This is crucial for arcs whose endpoints may change after center/radius adjustments
    ' Instead of trying to modify collection items directly, we'll recreate the endpoints array
    
    Dim updatedEndpoints As Variant
    
    Select Case entity.ObjectName
        Case "AcDbLine"
            Dim line As AcadLine
            Set line = entity
            updatedEndpoints = Array(line.startPoint, line.endPoint)
            
        Case "AcDbArc"
            Dim arc As AcadArc
            Set arc = entity
            ' Recalculate arc endpoints with current center, radius, and angles
            Dim arcStartPt(2) As Double, arcEndPt(2) As Double
            arcStartPt(0) = arc.center(0) + arc.radius * Cos(arc.startAngle)
            arcStartPt(1) = arc.center(1) + arc.radius * Sin(arc.startAngle)
            arcStartPt(2) = arc.center(2)
            arcEndPt(0) = arc.center(0) + arc.radius * Cos(arc.endAngle)
            arcEndPt(1) = arc.center(1) + arc.radius * Sin(arc.endAngle)
            arcEndPt(2) = arc.center(2)
            updatedEndpoints = Array(arcStartPt, arcEndPt)
            
        Case "AcDbPolyline"
            Dim pline As AcadLWPolyline
            Set pline = entity
            ' Get updated coordinates
            Dim coords As Variant
            coords = pline.Coordinates
            Dim StartPt(2) As Double, EndPt(2) As Double
            StartPt(0) = coords(0): StartPt(1) = coords(1): StartPt(2) = 0
            Dim lastIndex As Integer
            lastIndex = UBound(coords) - 1
            EndPt(0) = coords(lastIndex - 1): EndPt(1) = coords(lastIndex): EndPt(2) = 0
            updatedEndpoints = Array(StartPt, EndPt)
            
        Case "AcDbSpline"
            Dim spline As AcadSpline
            Set spline = entity
            ' Safely attempt to read start/end points; fall back to bounding box if unavailable
            On Error Resume Next
            Dim tStart As Variant, tEnd As Variant
            tStart = spline.startPoint
            tEnd = spline.endPoint
            If Err.Number <> 0 Then
                Err.Clear
                Dim bbMin2(2) As Double, bbMax2(2) As Double
                spline.GetBoundingBox bbMin2, bbMax2
                tStart = bbMin2
                tEnd = bbMax2
            End If
            On Error GoTo 0
            updatedEndpoints = Array(tStart, tEnd)
    End Select
    
    ' Replace the item in the collection by removing and adding at the same position
    ' First, check if we need to preserve order
    If entityIndex <= endpoints.count Then
        endpoints.Remove entityIndex
        If entityIndex = 1 Then
            endpoints.Add updatedEndpoints, , 1
        ElseIf entityIndex > endpoints.count Then
            endpoints.Add updatedEndpoints
        Else
            endpoints.Add updatedEndpoints, , entityIndex
        End If
    End If
End Sub

' VBA does not have Atan2, so we define our own
Private Function Atan2(Y As Double, X As Double) As Double
    If X > 0 Then
        Atan2 = Atn(Y / X)
    ElseIf X < 0 Then
        If Y >= 0 Then
            Atan2 = Atn(Y / X) + 3.14159265358979
        Else
            Atan2 = Atn(Y / X) - 3.14159265358979
        End If
    Else ' x = 0
        If Y > 0 Then
            Atan2 = 3.14159265358979 / 2
        ElseIf Y < 0 Then
            Atan2 = -3.14159265358979 / 2
        Else
            Atan2 = 0 ' undefined, return 0
        End If
    End If
End Function

Attribute VB_Name = "M_HexagonDetect"
' BricsCAD VBA Macro: Polygon Detection
' Detects polygons formed by connected lines in the drawing
' Finds chains of connected lines and reports polygon information

Option Explicit

' Global tolerance value for line connection detection
Private Const GLOBAL_TOLERANCE As Double = 0.01

' List of lateral widths to check for hexagons (in drawing units)
Private Const LATERAL_WIDTHS As String = "5,10"  ' Example: "5,10,15,25"
Private Const WIDTH_TOLERANCE_PERCENT As Double = 0.01 ' 1% margin of error

' Progress bar settings
Private Const PROGRESS_THRESHOLD As Integer = 100 ' Show progress bar if more than this many lines
Private Const PROGRESS_INTERVAL As Integer = 10 ' Update progress every N percent

Public Sub DetectPolygons()
    Dim doc As AcadDocument
    Set doc = ThisDrawing
    
    ' Ensure Hexagonos layer exists and is green
    Call EnsureHexagonosLayer
    
    ' Ensure Puncionadeira layer exists and is red
    Call EnsurePuncionadeiraLayer
    
    Dim lines As collection
    Set lines = New collection
    
    Dim ent As AcadEntity
    ' Collect all lines in the drawing
    For Each ent In doc.modelSpace
        If ent.ObjectName = "AcDbLine" Then
            lines.Add ent
        End If
    Next
    
    Debug.Print "Found " & lines.count & " lines in the drawing"
    Debug.Print "Starting polygon detection with tolerance: " & GLOBAL_TOLERANCE
    Debug.Print "========================================================"
    
    ' Determine if we need to show progress
    Dim showProgress As Boolean
    showProgress = lines.count > PROGRESS_THRESHOLD
    
    If showProgress Then
        Debug.Print "Processing " & lines.count & " lines - progress will be shown..."
        Debug.Print "Progress: [          ] 0%"
    End If
    
    Dim processedLines As collection
    Set processedLines = New collection
    
    Dim polygonCount As Long
    Dim hexagonCount As Long
    Dim puncionadeiraCount As Long
    polygonCount = 0
    hexagonCount = 0
    puncionadeiraCount = 0
    
    Dim lineIndex As Long
    Dim startLine As AcadLine
    Dim polygon As collection
    Dim polyLine As AcadLine
    Dim j As Long
    
    ' Progress tracking variables
    Dim lastProgressPercent As Long
    lastProgressPercent = 0

    For lineIndex = 1 To lines.count
        ' Update progress bar if needed
        If showProgress Then
            Dim currentPercent As Long
            currentPercent = CLng((lineIndex * 100) / IIf(lines.count = 0, 1, lines.count))
            
            If currentPercent >= lastProgressPercent + PROGRESS_INTERVAL Then
                Call UpdateProgressBar(currentPercent)
                lastProgressPercent = currentPercent
            End If
        End If
        
        Set startLine = lines(lineIndex)

        ' Skip if this line was already processed in a polygon
        If Not IsLineProcessed(startLine, processedLines) Then
            Set polygon = FindPolygon(startLine, lines, GLOBAL_TOLERANCE)

            If Not polygon Is Nothing Then
                If polygon.count >= 3 Then
                    polygonCount = polygonCount + 1
                    Call ReportPolygon(polygon, polygonCount)
                    
                    ' Check if it's a hexagon and move to appropriate layer
                    If polygon.count = 6 Then
                        hexagonCount = hexagonCount + 1
                        
                        ' Check if hexagon has lateral width matching our list
                        Dim lateralWidth As Double
                        lateralWidth = GetHexagonLateralWidth(polygon)
                        
                        If IsWidthInList(lateralWidth) Then
                            puncionadeiraCount = puncionadeiraCount + 1
                            Call MovePolygonToPuncionadeiraLayer(polygon)
                            Debug.Print "  --> Hexagon with lateral width " & Format(lateralWidth, "0.000") & " moved to 'Puncionadeira' layer"
                        Else
                            Call MovePolygonToHexagonosLayer(polygon)
                            Debug.Print "  --> Hexagon with lateral width " & Format(lateralWidth, "0.000") & " moved to 'Hexagonos' layer"
                        End If
                    End If

                    ' Mark all lines in this polygon as processed
                    For j = 1 To polygon.count
                        Set polyLine = polygon(j)
                        processedLines.Add polyLine
                    Next j
                End If
            End If
        End If
    Next lineIndex
    
    ' Complete progress bar if shown
    If showProgress Then
        Call UpdateProgressBar(100)
        Debug.Print "" ' Add blank line after progress
    End If
    
    Debug.Print ""
    Debug.Print "Total polygons found: " & polygonCount
    Debug.Print "Total hexagons found: " & hexagonCount
    Debug.Print "Hexagons moved to 'Hexagonos' layer: " & (hexagonCount - puncionadeiraCount)
    Debug.Print "Hexagons moved to 'Puncionadeira' layer: " & puncionadeiraCount
    Debug.Print "Polygon detection completed."
End Sub

' Finds a polygon starting from a given line
Private Function FindPolygon(startLine As AcadLine, allLines As collection, TOLERANCE As Double) As collection
    Dim polygon As collection
    Set polygon = New collection
    
    Dim visitedLines As collection
    Set visitedLines = New collection
    
    polygon.Add startLine
    visitedLines.Add startLine
    
    Dim currentLine As AcadLine
    Set currentLine = startLine
    Dim currentEndPoint As Variant
    currentEndPoint = currentLine.endPoint
    
    Dim maxIterations As Long
    maxIterations = 50 ' Prevent infinite loops
    Dim iteration As Long
    iteration = 0
    
    Do While iteration < maxIterations
        iteration = iteration + 1
        
        Dim nextLine As AcadLine
        Set nextLine = FindConnectedLine(currentEndPoint, allLines, visitedLines, TOLERANCE)
        
        If nextLine Is Nothing Then
            ' No more connected lines found
            Exit Do
        End If
        
        ' Determine which end of the next line to use
        Dim nextEndPoint As Variant
        If IsPointsEqual(nextLine.startPoint, currentEndPoint, TOLERANCE) Then
            nextEndPoint = nextLine.endPoint
        Else
            nextEndPoint = nextLine.startPoint
        End If
        
        ' Check if this line connects back to the start (closes the polygon)
        If IsPointsEqual(nextEndPoint, startLine.startPoint, TOLERANCE) Then
            polygon.Add nextLine
            Exit Do ' Closed polygon found
        End If
        
        ' Add the line to the polygon and continue
        polygon.Add nextLine
        visitedLines.Add nextLine
        Set currentLine = nextLine
        currentEndPoint = nextEndPoint
    Loop
    
    ' Verify it's a closed polygon
    If polygon.count >= 3 Then
        Dim firstLine As AcadLine
        Dim lastLine As AcadLine
        Set firstLine = polygon(1)
        Set lastLine = polygon(polygon.count)
        
        ' Check if polygon is properly closed
        Dim lastEndPoint As Variant
        If IsPointsEqual(lastLine.startPoint, currentEndPoint, TOLERANCE) Then
            lastEndPoint = lastLine.endPoint
        Else
            lastEndPoint = lastLine.startPoint
        End If
        
        If Not IsPointsEqual(lastEndPoint, firstLine.startPoint, TOLERANCE) Then
            ' Not a closed polygon, return empty collection
            Set polygon = New collection
        End If
    Else
        ' Less than 3 sides, not a polygon
        Set polygon = New collection
    End If
    
    Set FindPolygon = polygon
End Function

' Finds a line connected to the given point
Private Function FindConnectedLine(point As Variant, allLines As collection, visitedLines As collection, TOLERANCE As Double) As AcadLine
    Dim line As AcadLine
        Dim i As Long
    
    For i = 1 To allLines.count
        Set line = allLines(i)
        
        ' Skip if already visited
        If Not IsLineInCollection(line, visitedLines) Then
            ' Check if the line's start point connects to our point
            If IsPointsEqual(line.startPoint, point, TOLERANCE) Then
                Set FindConnectedLine = line
                Exit Function
            End If
            ' Also check if the line's end point connects to our point
            If IsPointsEqual(line.endPoint, point, TOLERANCE) Then
                Set FindConnectedLine = line
                Exit Function
            End If
        End If
    Next i
    
    Set FindConnectedLine = Nothing
End Function

' Checks if two points are equal within tolerance
Private Function IsPointsEqual(point1 As Variant, point2 As Variant, TOLERANCE As Double) As Boolean
    Dim dx As Double, dy As Double, dz As Double
    dx = point1(0) - point2(0)
    dy = point1(1) - point2(1)
    dz = point1(2) - point2(2)
    
    IsPointsEqual = Sqr(dx * dx + dy * dy + dz * dz) <= TOLERANCE
End Function

' Checks if a line is in a collection
Private Function IsLineInCollection(line As AcadLine, collection As collection) As Boolean
    Dim item As AcadLine
        Dim i As Long
    
    For i = 1 To collection.count
        Set item = collection(i)
        If item.Handle = line.Handle Then
            IsLineInCollection = True
            Exit Function
        End If
    Next i
    
    IsLineInCollection = False
End Function

' Checks if a line was already processed
Private Function IsLineProcessed(line As AcadLine, processedLines As collection) As Boolean
    IsLineProcessed = IsLineInCollection(line, processedLines)
End Function

' Reports information about a found polygon
Private Sub ReportPolygon(polygon As collection, polygonNumber As Long)
    Debug.Print "Polygon #" & polygonNumber & ":"
    Debug.Print "  Number of sides: " & polygon.count
    Debug.Print "  Line handles: ";
    
    Dim line As AcadLine
    Dim i As Long
    For i = 1 To polygon.count
        Set line = polygon(i)
        Debug.Print line.Handle;
        If i < polygon.count Then Debug.Print ", ";
    Next i
    Debug.Print ""
    
    ' Calculate and report polygon properties
    Dim perimeter As Double
    perimeter = CalculatePolygonPerimeter(polygon)
    Debug.Print "  Perimeter: " & Format(perimeter, "0.000")
    
    Dim area As Double
    area = CalculatePolygonArea(polygon)
    Debug.Print "  Area: " & Format(area, "0.000")
    
    Debug.Print ""
End Sub

' Calculates the perimeter of a polygon
Private Function CalculatePolygonPerimeter(polygon As collection) As Double
    Dim totalLength As Double
    totalLength = 0
    
    Dim line As AcadLine
        Dim i As Long
    For i = 1 To polygon.count
        Set line = polygon(i)
        totalLength = totalLength + line.Length
    Next i
    
    CalculatePolygonPerimeter = totalLength
End Function

' Calculates the area of a polygon using the shoelace formula
Private Function CalculatePolygonArea(polygon As collection) As Double
    If polygon.count < 3 Then
        CalculatePolygonArea = 0
        Exit Function
    End If
    
    Dim area As Double
    area = 0
    
    Dim line As AcadLine
    Dim i As Long
    For i = 1 To polygon.count
        Set line = polygon(i)
        Dim x1 As Double, y1 As Double
        Dim x2 As Double, y2 As Double
        
        x1 = line.startPoint(0)
        y1 = line.startPoint(1)
        x2 = line.endPoint(0)
        y2 = line.endPoint(1)
        
        area = area + (x1 * y2 - x2 * y1)
    Next i
    
    CalculatePolygonArea = Abs(area) / 2
End Function

' Helper function to highlight found polygons (optional)
Public Sub HighlightPolygon(polygon As collection, colorIndex As Integer)
    Dim line As AcadLine
    Dim i As Long
    For i = 1 To polygon.count
        Set line = polygon(i)
        line.Color = colorIndex
    Next i
    
    ThisDrawing.Regen acAllViewports
End Sub

' Ensures the Hexagonos layer exists and is configured as green
Private Sub EnsureHexagonosLayer()
    Dim doc As AcadDocument
    Set doc = ThisDrawing
    
    Dim layerName As String
    layerName = "Hexagonos"
    
    Dim hexagonosLayer As AcadLayer
    
    ' Try to get the layer, create it if it doesn't exist
    On Error GoTo CreateLayer
    Set hexagonosLayer = doc.layers(layerName)
    GoTo ConfigureLayer
    
CreateLayer:
    Set hexagonosLayer = doc.layers.Add(layerName)
    Debug.Print "Created layer '" & layerName & "'"
    
ConfigureLayer:
    ' Set layer color to green (color index 3)
   '  hexagonosLayer.color = acGreen
    hexagonosLayer.Linetype = "Continuous"
    
    Debug.Print "Configured layer '" & layerName & "' as green"
End Sub

' Moves all lines of a polygon to the Hexagonos layer
Private Sub MovePolygonToHexagonosLayer(polygon As collection)
    Dim line As AcadLine
        Dim i As Long
    
    For i = 1 To polygon.count
        Set line = polygon(i)
        ' Ensure the line uses the layer color by setting its color to ByLayer
        line.Color = acByLayer
        line.layer = "Hexagonos"
    Next i
End Sub

' Ensures the Puncionadeira layer exists and is configured as red
Private Sub EnsurePuncionadeiraLayer()
    Dim doc As AcadDocument
    Set doc = ThisDrawing
    
    Dim layerName As String
    layerName = "Puncionadeira"
    
    Dim puncionadeiraLayer As AcadLayer
    
    ' Try to get the layer, create it if it doesn't exist
    On Error GoTo CreateLayer
    Set puncionadeiraLayer = doc.layers(layerName)
    GoTo ConfigureLayer
    
CreateLayer:
    Set puncionadeiraLayer = doc.layers.Add(layerName)
    Debug.Print "Created layer '" & layerName & "'"
    
ConfigureLayer:
    ' Set layer color to red (color index 1)
    puncionadeiraLayer.Color = acRed
    puncionadeiraLayer.Linetype = "Continuous"
    
    Debug.Print "Configured layer '" & layerName & "' as red"
End Sub

' Moves all lines of a polygon to the Puncionadeira layer
Private Sub MovePolygonToPuncionadeiraLayer(polygon As collection)
    Dim line As AcadLine
        Dim i As Long
    
    For i = 1 To polygon.count
        Set line = polygon(i)
        ' Ensure the line uses the layer color by setting its color to ByLayer
        line.Color = acByLayer
        line.layer = "Puncionadeira"
    Next i
End Sub

' Calculates the lateral width of a hexagon (distance between parallel sides)
Private Function GetHexagonLateralWidth(polygon As collection) As Double
    If polygon.count <> 6 Then
        GetHexagonLateralWidth = 0
        Exit Function
    End If
    
    ' For a regular hexagon, we need to find the distance between parallel sides
    ' We'll calculate the distance from each line to all other lines and find the maximum
    Dim maxDistance As Double
    maxDistance = 0
    
    Dim line1 As AcadLine, line2 As AcadLine
        Dim i As Long, j As Long
    
    For i = 1 To polygon.count
        Set line1 = polygon(i)
        For j = i + 1 To polygon.count
            Set line2 = polygon(j)
            
            ' Check if lines are approximately parallel
            If AreLinesParallel(line1, line2) Then
                Dim distance As Double
                distance = DistanceBetweenParallelLines(line1, line2)
                If distance > maxDistance Then
                    maxDistance = distance
                End If
            End If
        Next j
    Next i
    
    GetHexagonLateralWidth = maxDistance
End Function

' Checks if two lines are approximately parallel
Private Function AreLinesParallel(line1 As AcadLine, line2 As AcadLine) As Boolean
    Dim dx1 As Double, dy1 As Double
    Dim dx2 As Double, dy2 As Double
    
    ' Calculate direction vectors
    dx1 = line1.endPoint(0) - line1.startPoint(0)
    dy1 = line1.endPoint(1) - line1.startPoint(1)
    dx2 = line2.endPoint(0) - line2.startPoint(0)
    dy2 = line2.endPoint(1) - line2.startPoint(1)
    
    ' Normalize the vectors
    Dim len1 As Double, len2 As Double
    len1 = Sqr(dx1 * dx1 + dy1 * dy1)
    len2 = Sqr(dx2 * dx2 + dy2 * dy2)
    
    If len1 = 0 Or len2 = 0 Then
        AreLinesParallel = False
        Exit Function
    End If
    
    dx1 = dx1 / len1
    dy1 = dy1 / len1
    dx2 = dx2 / len2
    dy2 = dy2 / len2
    
    ' Calculate cross product (for 2D, this is dx1*dy2 - dy1*dx2)
    Dim crossProduct As Double
    crossProduct = Abs(dx1 * dy2 - dy1 * dx2)
    
    ' Lines are parallel if cross product is close to 0
    AreLinesParallel = crossProduct < 0.1 ' Tolerance for "approximately parallel"
End Function

' Calculates distance between two parallel lines
Private Function DistanceBetweenParallelLines(line1 As AcadLine, line2 As AcadLine) As Double
    ' Use point-to-line distance formula
    ' Distance from point (x0,y0) to line ax + by + c = 0 is |ax0 + by0 + c| / sqrt(a^2 + b^2)
    
    ' Get line1 equation coefficients (ax + by + c = 0)
    Dim dx As Double, dy As Double
    dx = line1.endPoint(0) - line1.startPoint(0)
    dy = line1.endPoint(1) - line1.startPoint(1)
    
    ' Normal vector to line1 is (-dy, dx)
    Dim a As Double, b As Double, c As Double
    a = -dy
    b = dx
    c = dy * line1.startPoint(0) - dx * line1.startPoint(1)
    
    ' Calculate distance from line2's start point to line1
    Dim x0 As Double, y0 As Double
    x0 = line2.startPoint(0)
    y0 = line2.startPoint(1)
    
    Dim distance As Double
    distance = Abs(a * x0 + b * y0 + c) / Sqr(a * a + b * b)
    
    DistanceBetweenParallelLines = distance
End Function

' Checks if a width matches any value in our lateral widths list (within tolerance)
Private Function IsWidthInList(width As Double) As Boolean
    Dim widthArray As Variant
    widthArray = Split(LATERAL_WIDTHS, ",")
    
    Dim i As Long
        For i = 0 To UBound(widthArray)
        Dim targetWidth As Double
        targetWidth = CDbl(Trim(widthArray(i)))
        
        ' Check if width is within tolerance percentage
        Dim TOLERANCE As Double
        TOLERANCE = targetWidth * WIDTH_TOLERANCE_PERCENT
        
        If Abs(width - targetWidth) <= TOLERANCE Then
            IsWidthInList = True
            Exit Function
        End If
    Next i
    
    IsWidthInList = False
End Function

' Updates and displays a text-based progress bar
Private Sub UpdateProgressBar(percent As Long)
    Dim progressBar As String
    Dim barLength As Long
    barLength = 10
    
    Dim filledLength As Long
    filledLength = CLng((percent * barLength) / 100)
    
    ' Build progress bar string
    progressBar = "Progress: ["
    
    Dim i As Long
    For i = 1 To barLength
        If i <= filledLength Then
            progressBar = progressBar & "="
        Else
            progressBar = progressBar & " "
        End If
    Next i
    
    progressBar = progressBar & "] " & percent & "%"
    
    ' Clear previous line and print new progress
    Debug.Print Chr(13) & progressBar;
    
    ' Force immediate update of the debug window
    DoEvents
End Sub

Attribute VB_Name = "M_LayerClean"
Public Sub LayerClean_Del(Optional ByVal layerNameParam As String = "")
    Dim acadDoc As Object ' AcadDocument
    Dim modelSpace As Object ' AcadModelSpace
    Dim entity As Object ' AcadEntity
    Dim layerName As String
    Dim objectsOnLayer As collection
    Dim objToDelete As Object
    Dim deletedCount As Long
    Dim i As Long

    deletedCount = 0

    ' --- Get layer name from form or parameter ---
    If layerNameParam = "" Then
        On Error Resume Next
        layerName = formPerfisul01.cbCamada02.Value
        If Err.Number <> 0 Then
            MsgBox "Erro ao acessar o controle de camada no formulário.", vbCritical, "Erro de Controle"
            Err.Clear
            Exit Sub
        End If
        On Error GoTo 0
        If layerName = "-- Selecione uma camada --" Or layerName = "" Then
            MsgBox "Por favor, selecione uma camada válida no formulário.", vbExclamation, "Seleção de Camada Inválida"
            Exit Sub
        End If
    Else
        layerName = layerNameParam
    End If

    On Error GoTo ErrorHandler

    ' --- Get the current document and model space ---
    Set acadDoc = ThisDrawing
    Set modelSpace = acadDoc.modelSpace

    ' --- Collect all objects on the specified layer ---
    Set objectsOnLayer = New collection
    For Each entity In modelSpace
        If entity.layer = layerName Then
            objectsOnLayer.Add entity
        End If
    Next entity

    If objectsOnLayer.count = 0 Then
        MsgBox "No objects found on layer '" & layerName & "'.", vbInformation
        GoTo Cleanup
    End If

    ' --- Delete all objects on the layer ---
    For i = objectsOnLayer.count To 1 Step -1
        Set objToDelete = objectsOnLayer(i)
        On Error Resume Next
        objToDelete.Delete
        If Err.Number = 0 Then
            deletedCount = deletedCount + 1
        Else
            Err.Clear
        End If
        On Error GoTo ErrorHandler
    Next i

    acadDoc.Regen acAllViewports
    MsgBox deletedCount & " object(s) deleted from layer '" & layerName & "'.", vbInformation

Cleanup:
    Set acadDoc = Nothing
    Set modelSpace = Nothing
    Set objectsOnLayer = Nothing
    Set entity = Nothing
    Set objToDelete = Nothing
    Exit Sub

ErrorHandler:
    MsgBox "An error occurred in LayerClean_Del: " & Err.Description & vbCrLf & _
           "Error Number: " & Err.Number & vbCrLf & _
           "Error Source: " & Err.Source, vbCritical, "Script Error"
    Resume Cleanup
End Sub

Attribute VB_Name = "M_MText_To_Text"
Option Explicit

' MText_To_Text: Convert MText objects on a specified layer to Text objects
' This preserves text content, location, height, rotation and layer
' Use the layer selection from formPerfisul01

Public Sub MText_To_Text(Optional ByVal layerNameParam As String = "")
    ' Variable declarations
    Dim acadDoc As Object ' AcadDocument
    Dim modelSpace As Object ' AcadModelSpace
    Dim entity As Object ' AcadEntity
    Dim mtextObj As Object ' AcadMText
    Dim layerName As String
    Dim mtextObjectsOnLayer As collection
    Dim i As Long
    Dim mTextCount As Long
    Dim conversionCount As Long
    
    ' --- Form Access and Input Validation ---
    If layerNameParam = "" Then
        On Error Resume Next
        layerName = formPerfisul01.cbCamada01.Value
        If Err.Number <> 0 Then
            MsgBox "Erro ao acessar o controle de camada no formulário.", vbCritical, "Erro de Controle"
            Err.Clear
            Exit Sub
        End If
        On Error GoTo 0
        If layerName = "-- Selecione uma camada --" Or layerName = "" Then
            MsgBox "Por favor, selecione uma camada válida.", vbExclamation, "Seleção de Camada"
            Exit Sub
        End If
    Else
        layerName = layerNameParam
    End If
    
    On Error GoTo ErrorHandler
    
    ' Get the current document and model space
    Set acadDoc = ThisDrawing
    Set modelSpace = acadDoc.modelSpace
    
    ' --- Search for MText objects in the specified layer ---
    Set mtextObjectsOnLayer = New collection
    For Each entity In modelSpace
        If entity.layer = layerName Then
            If entity.ObjectName = "AcDbMText" Then
                mtextObjectsOnLayer.Add entity
            End If
        End If
    Next entity
    
    mTextCount = mtextObjectsOnLayer.count
    If mTextCount = 0 Then
      '   MsgBox "Nenhum objeto MText encontrado na camada '" & layerName & "'.", vbInformation
        GoTo Cleanup
    End If
    
    ' Show progress message
   '  MsgBox "Encontrados " & mTextCount & " objetos MText na camada '" & layerName & "'." & vbCrLf & _
   '         "Tentando convertê-los para objetos de texto...", vbInformation
      ' --- Try to explode MText objects first ---
    ' This is a more reliable way to convert MText to Text in BricsCAD
    ' Process each MText object individually for greater reliability
    conversionCount = 0
    
    For Each mtextObj In mtextObjectsOnLayer        ' Build a simple explode command for each object
        Dim explodeCmd As String
        On Error Resume Next
        
        ' Direct selection and explode of just this one MText object
        explodeCmd = "_SELECT (handent """ & mtextObj.Handle & """) " & vbCr & "_EXPLODE " & vbCr
        
        ' Execute the commands
        acadDoc.SendCommand explodeCmd
        
        If Err.Number = 0 Then
            conversionCount = conversionCount + 1
        Else
            Debug.Print "Error exploding MText: " & mtextObj.Handle & " - " & Err.Description
            Err.Clear
        End If
    Next mtextObj
    
    ' Update display after all operations
    acadDoc.Regen acAllViewports
          ' Pause to let BricsCAD process the commands
        Wait 1
        
        ' Check if explosion approach worked
        If conversionCount > 0 Then
            ' MsgBox conversionCount & " de " & mTextCount & " objetos MText foram explodidos na camada '" & _
                   layerName & "'.", vbInformation
              ' Check if we need to continue with alternate approach
            If conversionCount >= mTextCount Then
                GoTo Cleanup ' All objects were processed successfully
            End If
        End If
        
        ' If we get here, some objects remain - fall back to manual conversion
    
    ' --- Fall back to manual conversion if explosion didn't work ---
    conversionCount = 0
    
    ' Re-collect MText objects as some might have been exploded
    Set mtextObjectsOnLayer = New collection
    For Each entity In modelSpace
        If entity.layer = layerName Then
            If entity.ObjectName = "AcDbMText" Then
                mtextObjectsOnLayer.Add entity
            End If
        End If
    Next entity
    
    mTextCount = mtextObjectsOnLayer.count
    If mTextCount = 0 Then
      '   MsgBox "Todos os objetos MText foram explodidos com sucesso.", vbInformation
        GoTo Cleanup
    End If
    
    ' Try alternative method: create text and delete originals
    For i = mTextCount To 1 Step -1 ' Process backwards for collection integrity
        Set mtextObj = mtextObjectsOnLayer(i)
        
        On Error Resume Next
        ' Get original MText properties
        Dim mtextContent As String
        Dim mtextInsertionPoint As Variant
        Dim mtextHeight As Double
        Dim mtextRotation As Double
        Dim mtextColor As Integer
        Dim mtextLayer As String
        Dim mtextStyle As String
        
        mtextContent = CleanMTextString(mtextObj.text) ' Use the helper function to clean formatting
        mtextInsertionPoint = mtextObj.InsertionPoint
        mtextHeight = mtextObj.height
        mtextRotation = 0 ' Default in case we can't get rotation
        
        On Error Resume Next
        mtextRotation = mtextObj.rotation
        If Err.Number <> 0 Then
            Err.Clear
        End If
        
        mtextColor = mtextObj.Color
        mtextLayer = mtextObj.layer
        mtextStyle = mtextObj.styleName
        
        ' Create new Text object with the same properties
        Dim newTextObj As Object
        Set newTextObj = modelSpace.AddText(mtextContent, mtextInsertionPoint, mtextHeight)
        newTextObj.rotation = mtextRotation
        newTextObj.layer = mtextLayer
        newTextObj.styleName = mtextStyle
        newTextObj.Color = mtextColor
        newTextObj.Update        ' Remove the original MText object using a targeted selection
        Dim eraseCmd As String
        eraseCmd = "_SELECT (handent """ & mtextObj.Handle & """) " & vbCr & "_ERASE " & vbCr
        
        On Error Resume Next
        acadDoc.SendCommand eraseCmd
        
        ' Short pause to allow command to complete
        Wait 0.2
        
        ' Verify the object was deleted
        Dim deleted As Boolean
        deleted = False
        Dim testHandle As String
        testHandle = mtextObj.Handle
        If Err.Number <> 0 Then
            ' Error accessing handle means the object was deleted
            deleted = True
            conversionCount = conversionCount + 1
            Err.Clear
        End If
        
        If Not deleted Then
            ' Try an alternative direct approach if the first method failed - use API method
            On Error Resume Next
            mtextObj.Delete  ' Try the API method
            Wait 0.2
            Wait 0.2
            conversionCount = conversionCount + 1
        End If
        
        On Error GoTo ErrorHandler ' Restore main error handler
    Next i
    
    ' Update the display and inform the user
    acadDoc.Regen acAllViewports
    MsgBox conversionCount & " de " & mTextCount & " objetos MText convertidos para Texto na camada '" & _
           layerName & "'.", vbInformation
    
Cleanup:
    Set acadDoc = Nothing
    Set modelSpace = Nothing
    Set mtextObjectsOnLayer = Nothing
    Set entity = Nothing
    Set mtextObj = Nothing
    Exit Sub
    
ErrorHandler:
    MsgBox "Ocorreu um erro: " & Err.Description & vbCrLf & _
           "Número do erro: " & Err.Number & vbCrLf & _
           "Fonte do erro: " & Err.Source, vbCritical, "Erro de Script"
    Resume Cleanup
End Sub

' --- Helper function to clean MText formatting ---
' Used to strip formatting from MText content for cleaner conversion to Text
Private Function CleanMTextString(ByVal s As String) As String
    Dim re As Object
    Set re = CreateObject("VBScript.RegExp")
    re.Global = True
    
    ' Remove {...} formatting codes
    re.Pattern = "\\{[^}]*\\}"
    s = re.Replace(s, "")
    
    ' Replace CR, LF, Tab, No-break space with a single space
    s = Replace(s, vbCr, " ")
    s = Replace(s, vbLf, " ")
    s = Replace(s, vbTab, " ")
    s = Replace(s, Chr(160), " ")
    
    ' Normalize multiple spaces to a single space
    re.Pattern = "\\s+" ' Match one or more whitespace characters
    s = re.Replace(s, " ")
    
    s = Trim(s) ' Trim leading/trailing spaces
    CleanMTextString = s
End Function

' Helper subroutine to add a small delay (in seconds)
Private Sub Wait(seconds As Double)
    Dim startTime As Double
    startTime = Timer
    Do While Timer < startTime + seconds
        DoEvents ' Allow the system to process other events
    Loop
End Sub

' Instructions to run:
' 1. Open BricsCAD.
' 2. Press ALT+F11 to open the VBA IDE (or type VBAIDE in the command line).
' 3. In the VBA IDE, go to File > Import File... and select this .vba file.
'    Alternatively, go to Insert > Module and paste this code into the new module.
' 4. Close the VBA IDE.
' 5. In BricsCAD, type VBARUN in the command line.
' 6. Select "MText_To_Text" from the list and click "Run".
' 7. Ensure that formPerfisul01 is loaded and a layer is selected in cbCamada01.

Attribute VB_Name = "M_ResizeAndColorCircles"
Option Explicit

Public Sub ResizeAndColorCircles()
    Dim acadDoc As Object ' AcadDocument
    Dim modelSpace As Object ' AcadModelSpace
    Dim entity As Object ' AcadEntity
    Dim circleObj As Object ' AcadCircle
    Dim otherCircleObj As Object ' AcadCircle
    Dim diametersArray As Variant
    Dim i As Integer
    Dim originalDiameter As Double
    Dim newDiameter As Double
    Dim targetDiameter As Double
     Dim margin As Double
    Dim lowerBound As Double
    Dim upperBound As Double
    Dim centerPoint As Variant
    Dim tempEntity As Object
    Dim entity_idx As Long ' Declare index for backward loop

    ' Additional variables for programmatic array creation
    Dim tempPairsCollection As collection
    Dim k_idx As Long ' Loop index for converting collection to array    ' Set the active document and model space
    On Error Resume Next
    Set acadDoc = ThisDrawing
    If acadDoc Is Nothing Then
        MsgBox "Could not get ThisDrawing. Make sure you are running this from BricsCAD.", vbCritical
        Exit Sub
    End If
    On Error GoTo 0
    
    Set modelSpace = acadDoc.modelSpace
    
    ' Get or create the "Puncionadeira" layer and set its color to red
    Dim puncionadeiraLayer As Object
    Set puncionadeiraLayer = GetOrCreateLayer(acadDoc, "Puncionadeira", acRed)

    ' 1. Programmatically build the array of diameter pairs.
    '    This allows for easier addition of a large number of pairs.
    Set tempPairsCollection = New collection

    ' Add your pairs here. Each line adds one pair.
    ' Format: tempPairsCollection.Add Array(OriginalDiameter, NewDiameter)
    tempPairsCollection.Add Array(1.6, 1.6)
    tempPairsCollection.Add Array(2, 2)
    tempPairsCollection.Add Array(3, 3)
    tempPairsCollection.Add Array(3.2, 3.2)
    tempPairsCollection.Add Array(3.4, 3.4)
    tempPairsCollection.Add Array(3.242, 1.9)
    tempPairsCollection.Add Array(4, 4)
    tempPairsCollection.Add Array(4.2, 4.2)
    tempPairsCollection.Add Array(4.4, 4.4)
    tempPairsCollection.Add Array(5, 5)
    tempPairsCollection.Add Array(6, 6)
    tempPairsCollection.Add Array(8.5, 8.5)
    tempPairsCollection.Add Array(9, 13.5)
    tempPairsCollection.Add Array(9.28, 13.5)
    tempPairsCollection.Add Array(21, 21)
    tempPairsCollection.Add Array(22, 22)
    tempPairsCollection.Add Array(28, 28)

    ' Add more pairs below as needed:
    ' tempPairsCollection.Add Array(25.0, 17.5)
    ' tempPairsCollection.Add Array(30.0, 22.5)

    ' Convert the collection to the 0-indexed diametersArray
    If tempPairsCollection.count > 0 Then
        ReDim diametersArray(0 To tempPairsCollection.count - 1)
        For k_idx = 0 To tempPairsCollection.count - 1
            diametersArray(k_idx) = tempPairsCollection(k_idx + 1) ' Collection is 1-indexed
        Next k_idx
    Else
        ' If no pairs are added, create an empty array so LBound/UBound don't fail,
        ' and the subsequent loop For i = LBound(diametersArray) To UBound(diametersArray)
        ' correctly does not iterate. (UBound will be -1, LBound will be 0)
        ReDim diametersArray(0 To -1)
    End If

    ' 2. Iterate the current drawing and search for every circle (iterate backwards)
    ' For entity_idx = modelSpace.Count - 1 To 0 Step -1 ' Previous loop structure
    entity_idx = modelSpace.count - 1 ' Initialize for Do While loop
    Do While entity_idx >= 0
        ' Before accessing Item(entity_idx), ensure entity_idx is still valid
        ' as modelSpace.Count might have changed due to deletions in previous iterations of this outer loop.
        If entity_idx >= modelSpace.count Then
            entity_idx = modelSpace.count - 1 ' Re-align index with the current end of the collection
            If entity_idx < 0 Then Exit Do     ' Collection is now empty, nothing more to process
        End If

        Set entity = modelSpace.item(entity_idx)

        If TypeOf entity Is AcadCircle Then
            Set circleObj = entity
            originalDiameter = circleObj.Diameter

            For i = LBound(diametersArray) To UBound(diametersArray)
                targetDiameter = diametersArray(i)(0)
                newDiameter = diametersArray(i)(1)

                ' with a safety margin of % for more or less.
                     margin = 0.01
                lowerBound = targetDiameter * (1 - margin)
                upperBound = targetDiameter * (1 + margin)

                If originalDiameter >= lowerBound And originalDiameter <= upperBound Then
                    ' Store center point before resizing
                    centerPoint = circleObj.center                    ' 3. Resize that circle to the corresponding value in the pair
                    circleObj.Diameter = newDiameter
                    
                    ' 4. Move the circle to the "Puncionadeira" layer and set its color to ByLayer
                    circleObj.layer = "Puncionadeira"
                    ' Set the object's color to ByLayer so it inherits the layer color
                    circleObj.Color = acByLayer
                    ' Set the linetype to Continuous
                    circleObj.Linetype = "Continuous"

                    ' 5. Delete every other circle concentric to that circle.
                    ' The inner loop (For k...) is generally fine as it iterates backwards.
                    Dim k As Long ' Use Long for index
                    For k = modelSpace.count - 1 To 0 Step -1
                        ' Check if k is out of bounds (it shouldn't be with a For...Step -1 loop, but as an extra safe guard)
                        If k >= modelSpace.count Then k = modelSpace.count - 1
                        If k < 0 Then Exit For ' modelSpace might have become empty

                        Set tempEntity = modelSpace.item(k)
                        If TypeOf tempEntity Is AcadCircle Then
                            Set otherCircleObj = tempEntity
                            ' Check if it's not the same circle (handle comparison) and if it's concentric
                            If Not otherCircleObj.Handle = circleObj.Handle Then
                                If PointsAreEqual(otherCircleObj.center, centerPoint) Then
                                    otherCircleObj.Delete
                                End If
                            End If
                        End If
                    Next k ' End of inner loop for deletion
                    
                    ' Exit the inner loop (diametersArray loop) once a match is found and processed for this circle
                    Exit For
                End If
            Next i
        End If
        entity_idx = entity_idx - 1 ' Decrement for the Do While loop
    ' Next entity_idx ' This was the end of the For loop
    Loop ' This is the end of the Do While loop

    acadDoc.Regen acAllViewports
    ' MsgBox "Circle processing complete.", vbInformation

End Sub

Private Function PointsAreEqual(p1 As Variant, p2 As Variant, Optional TOLERANCE As Double = 0.0001) As Boolean
    ' Helper function to compare two points with a tolerance
    If Abs(p1(0) - p2(0)) < TOLERANCE And _
       Abs(p1(1) - p2(1)) < TOLERANCE And _
       Abs(p1(2) - p2(2)) < TOLERANCE Then
        PointsAreEqual = True
    Else
        PointsAreEqual = False
    End If
End Function

Private Function GetOrCreateLayer(acadDoc As Object, layerName As String, colorIndex As Integer) As Object
    Dim layer As Object
    Dim layers As Object
    
    ' Get the layers collection from the document
    Set layers = acadDoc.layers
    
    ' Try to get the layer if it exists
    On Error Resume Next
    Set layer = layers.item(layerName)
    On Error GoTo 0
    
    ' If the layer doesn't exist, create it
    If layer Is Nothing Then
        Set layer = layers.Add(layerName)
        layer.Color = colorIndex
    End If
    
    ' Return the layer object
    Set GetOrCreateLayer = layer
End Function

' To run this macro in BricsCAD:
' 1. Open BricsCAD.
' 2. Press ALT+F11 to open the VBA IDE (or type VBAIDE in the command line).
' 3. In the VBA IDE, go to Insert > Module.
' 4. Paste this code into the module.
' 5. Close the VBA IDE.
' 6. In BricsCAD, type VBARUN in the command line.
' 7. Select "ResizeAndColorCircles" from the list and click "Run".
' Make sure you have a drawing open with circles to test.

Attribute VB_Name = "M_TextCopier"
Option Explicit

Dim i As Long


Public Sub TextCopier_Add(Optional ByVal layerNameParam As String = "")
    Dim acadDoc As Object ' AcadDocument
    Dim modelSpace As Object ' AcadModelSpace
    Dim entity As Object ' AcadEntity
    Dim textObj As Object ' AcadText
    Dim layerName As String
    Dim objectsOnLayer As collection
    Dim textObjectsOnLayer As collection
    Dim i As Long
    Dim userInputText As String
    Dim copyDistance As Double
    Dim originalPoint As Variant
    Dim newPoint As Variant
    Dim rotationAngle As Double
    Dim dx As Double
    Dim dy As Double
    Dim copiedTextObj As Object
    Dim objToExplode As Object
    Dim explodedItems As Variant

    ' --- Form Access and Input Validation ---
    If layerNameParam = "" Then
        On Error Resume Next
        layerName = formPerfisul01.cbCamada01.Value
        If Err.Number <> 0 Then
            MsgBox "Erro ao acessar o controle de camada no formulário.", vbCritical, "Erro de Controle"
            Err.Clear
            Exit Sub
        End If
        On Error GoTo 0
        If layerName = "-- Selecione uma camada --" Or layerName = "" Then
            MsgBox "Por favor, selecione uma camada válida.", vbExclamation, "Seleção de Camada"
            Exit Sub
        End If
    Else
        layerName = layerNameParam
    End If

    ' Calculate copy distance based on the height of the source text object (1.85 * height)
    ' Will be set inside the loop for each text object

    On Error GoTo ErrorHandler

    ' Get the current document and model space
    Set acadDoc = ThisDrawing
    Set modelSpace = acadDoc.modelSpace

    ' --- Call MText_To_Text to handle MText conversion and explosion ---
    Call MText_To_Text(layerName)

    ' --- The explosion loop and manual MText conversion are no longer needed here,
    ' --- as MText_To_Text handles these operations.

    ' Regenerate to reflect any changes made by MText_To_Text
    acadDoc.Regen acAllViewports

    ' --- 3. Search all text objects in layer 'Gravação' ---
    Set textObjectsOnLayer = New collection
    For Each entity In modelSpace ' Re-iterate modelspace as new text entities might exist after MText_To_Text
        If entity.layer = layerName Then
            If TypeOf entity Is AcadText Then
                textObjectsOnLayer.Add entity
            End If
        End If
    Next entity    ' --- 4. If there is none, end script. Else, get text from form control ---
    If textObjectsOnLayer.count = 0 Then
        ' MsgBox "Nenhum objeto de texto encontrado na camada '" & layerName & "' após a conversão.", vbInformation
        GoTo Cleanup
    End If


    ' Get the text from the form control cbTexto01
    On Error Resume Next
    userInputText = formPerfisul01.cbTexto01.Value
    If Err.Number <> 0 Then
        MsgBox "Erro ao acessar o controle de texto no formulário.", vbCritical, "Erro de Controle"
        Err.Clear
        GoTo Cleanup
    End If
    On Error GoTo ErrorHandler
    If Trim(userInputText) = "" Then
        MsgBox "Por favor, digite o texto a ser adicionado no campo 'Texto'.", vbExclamation, "Texto não informado"
        GoTo Cleanup
    End If

    ' --- 5. Copy all text objects 8mm 'down'. ---
    ' --- 6. Modify the content of copied text to the inputed value ---
    For Each textObj In textObjectsOnLayer
        Set entity = textObj ' To be explicit that textObj is an AcadEntity

        ' Calculate copy distance based on the height of the source text object
        copyDistance = 1.85 * entity.height

        ' Use the anchor point that matches the justification so the copied text moves relative
        ' to the same reference (fixes Bottom Center staying in place).
        If entity.Alignment = acAlignmentLeft Then
            originalPoint = entity.InsertionPoint
        Else
            originalPoint = entity.TextAlignmentPoint
        End If
        rotationAngle = entity.rotation ' This is in Radians

        ' Calculate offset based on rotation
        ' "Down" relative to text: dx = distance * sin(angle), dy = distance * -cos(angle)
        dx = copyDistance * Sin(rotationAngle)
        dy = copyDistance * (-Cos(rotationAngle))

        ReDim newPoint(0 To 2) As Double
        newPoint(0) = originalPoint(0) + dx
        newPoint(1) = originalPoint(1) + dy
        newPoint(2) = originalPoint(2) ' Preserve Z coordinate

        ' Create a copy of the text object
        Set copiedTextObj = entity.Copy

        ' Modify the copied text
        ' For non-left justifications (e.g., Bottom Center) AutoCAD uses TextAlignmentPoint
        ' to anchor the text; setting both ensures the copy moves the expected 8mm down.
        copiedTextObj.InsertionPoint = newPoint
        copiedTextObj.TextAlignmentPoint = newPoint
        copiedTextObj.TextString = userInputText

        ' Ensure the copied text is on the correct layer (Copy method should preserve it, but good to be sure)
        If copiedTextObj.layer <> layerName Then
            copiedTextObj.layer = layerName
        End If
        copiedTextObj.Update ' Refresh the copied entity
    Next textObj

    acadDoc.Regen acAllViewports
    MsgBox "Objetos de texto copiados e modificados com sucesso.", vbInformation

Cleanup:
    Set acadDoc = Nothing
    Set modelSpace = Nothing
    Set objectsOnLayer = Nothing
    Set textObjectsOnLayer = Nothing
    Set entity = Nothing
    Set textObj = Nothing
    Set copiedTextObj = Nothing
    Set objToExplode = Nothing
    Exit Sub

ErrorHandler:
    MsgBox "Ocorreu um erro: " & Err.Description & vbCrLf & _
           "Número do erro: " & Err.Number & vbCrLf & _
           "Fonte do erro: " & Err.Source, vbCritical, "Erro de Script"
    Resume Cleanup
End Sub


Public Sub TextCopier_Del(Optional ByVal layerNameParam As String = "")
    Dim acadDoc As Object ' AcadDocument
    Dim modelSpace As Object ' AcadModelSpace
    Dim entity As Object ' AcadEntity
    Dim textObj As Object ' AcadText
    Dim layerName As String
    Dim objectsOnLayer As collection
    Dim textObjectsOnLayer As collection
    Dim textToDeleteValue As String
    Dim objToExplode As Object
    Dim explodedItems As Variant
    Dim deletedCount As Long
    deletedCount = 0

    ' --- Form Access and Input Validation ---
    ' Directly reference the form controls (formPerfisul01 must be loaded)
    If layerNameParam = "" Then
        On Error Resume Next
        layerName = formPerfisul01.cbCamada01.Value
        If Err.Number <> 0 Then
            MsgBox "Erro ao acessar o controle de camada no formulário.", vbCritical, "Erro de Controle"
            Err.Clear
            Exit Sub
        End If
        On Error GoTo 0
        If layerName = "-- Selecione uma camada --" Or layerName = "" Then
            MsgBox "Por favor, selecione uma camada válida no formulário.", vbExclamation, "Seleção de Camada Inválida"
            Exit Sub
        End If
    Else
        layerName = layerNameParam
    End If

    On Error Resume Next
    textToDeleteValue = formPerfisul01.cbTexto01.Value
    If Err.Number <> 0 Then
        MsgBox "Erro ao acessar o controle de texto no formulário.", vbCritical, "Erro de Controle"
        Err.Clear
        Exit Sub
    End If
    On Error GoTo 0
    If Trim(textToDeleteValue) = "" Then
        MsgBox "Por favor, digite o texto a ser excluído no campo 'Texto' do formulário.", vbExclamation, "Texto para exclusão não informado"
        Exit Sub
    End If

    ' --- Main Logic ---
    On Error GoTo ErrorHandler ' Set main error handler for the rest of the sub

    ' Get the current document and model space
    Set acadDoc = ThisDrawing
    Set modelSpace = acadDoc.modelSpace

    ' --- 1. Search for all objects in the specified layer ---
    Set objectsOnLayer = New collection
    For Each entity In modelSpace
        If entity.layer = layerName Then
            objectsOnLayer.Add entity
        End If
    Next entity

    ' --- 2. If there is none, end script. Else, explode them ---
    If objectsOnLayer.count = 0 Then
        MsgBox "Nenhum objeto encontrado na camada '" & layerName & "'.", vbInformation
        GoTo Cleanup
    End If

    ' Explode collected objects (iterating 4 times, similar to TextCopier_Add)
    Dim explosionCycle As Long
    For explosionCycle = 1 To 4 ' Corrected loop syntax
        ' Re-collect objects on the layer in each cycle as new ones might appear from explosions
        Set objectsOnLayer = New collection
        For Each entity In modelSpace
            If entity.layer = layerName Then
                objectsOnLayer.Add entity
            End If
        Next entity
        
        If objectsOnLayer.count = 0 Then Exit For ' No more objects to explode on this layer

        For Each objToExplode In objectsOnLayer
            On Error Resume Next ' To skip objects that cannot be exploded
            explodedItems = objToExplode.Explode
            If Err.Number <> 0 Then
                Err.Clear
            End If
            On Error GoTo ErrorHandler ' Restore main error handler
        Next objToExplode
    Next explosionCycle
    
    ' Regenerate to reflect explosions before searching for text
    acadDoc.Regen acAllViewports

    ' --- 3. Search all text objects in the specified layer ---
    Set textObjectsOnLayer = New collection
    For Each entity In modelSpace ' Re-iterate modelspace as new text entities might exist after explosion
        If entity.layer = layerName Then
            If TypeOf entity Is AcadText Then
                textObjectsOnLayer.Add entity
            End If
        End If
    Next entity

    ' --- 4. If there are no text objects, end script. Else, get text to delete from form control ---
    If textObjectsOnLayer.count = 0 Then
        MsgBox "Nenhum objeto de texto encontrado na camada '" & layerName & "' após a explosão.", vbInformation
        GoTo Cleanup
    End If

    ' --- 5. Delete text objects with value equal to textToDeleteValue ---
    For Each textObj In textObjectsOnLayer
        On Error Resume Next ' In case of issues with a specific text object
        If textObj.TextString = textToDeleteValue Then
            textObj.Delete
            If Err.Number = 0 Then ' Check if delete was successful
                deletedCount = deletedCount + 1
            Else
                ' Optionally log or inform about a text object that couldn't be deleted
                Err.Clear
            End If
        End If
        On Error GoTo ErrorHandler ' Restore main error handler
    Next textObj

    acadDoc.Regen acAllViewports
    MsgBox deletedCount & " objeto(s) de texto correspondente(s) a '" & textToDeleteValue & "' excluído(s) com sucesso da camada '" & layerName & "'.", vbInformation

Cleanup:
    Set acadDoc = Nothing
    Set modelSpace = Nothing
    Set objectsOnLayer = Nothing
    Set textObjectsOnLayer = Nothing
    Set entity = Nothing
    Set textObj = Nothing
    Set objToExplode = Nothing
    Exit Sub

ErrorHandler:
    MsgBox "Ocorreu um erro em TextCopier_Del: " & Err.Description & vbCrLf & _
           "Número do erro: " & Err.Number & vbCrLf & _
           "Fonte do erro: " & Err.Source, vbCritical, "Erro de Script"
    Resume Cleanup
End Sub

' Instructions to run:
' 1. Open BricsCAD.
' 2. Press ALT+F11 to open the VBA IDE (or type VBAIDE in the command line).
' 3. In the VBA IDE, go to File > Import File... and select this .vba file.
'    Alternatively, go to Insert > Module and paste this code into the new module.
' 4. Close the VBA IDE.
' 5. In BricsCAD, type VBARUN in the command line.
' 6. Select "TextCopier_Main" from the list and click "Run".
' 7. Ensure your drawing has a layer named "Gravação" with some objects and text entities for testing.

Attribute VB_Name = "M_TextSorter"
Option Explicit

Public Sub TextSorter_IndexTexts()
    Dim acadDoc As Object ' AcadDocument
    Dim modelSpace As Object ' AcadModelSpace
    Dim entity As Object ' AcadEntity
    Dim textObj As Object ' AcadText
    Dim layerName As String
    Dim ignoreValue As String
    Dim textObjects As collection
    Dim textData() As Variant
    Dim i As Long, j As Long
    Dim temp As Variant
    Dim indexLayer As Object
    Dim foundIndexLayer As Boolean
    Dim indexText As Object
    Dim indexValue As String
    Dim indexHeight As Double
    Dim indexPoint(0 To 2) As Double
    Dim offsetX As Double

    ' 1. Get layer and ignore value from form
    On Error Resume Next
    layerName = formPerfisul01.cbCamada01.Value
    ignoreValue = formPerfisul01.cbTexto01.Value
    If Err.Number <> 0 Or layerName = "" Or layerName = "-- Selecione uma camada --" Then
        MsgBox "Selecione uma camada válida no formulário.", vbExclamation
        Exit Sub
    End If
    On Error GoTo 0

    Set acadDoc = ThisDrawing
    Set modelSpace = acadDoc.modelSpace
    Set textObjects = New collection

    ' 2. Collect all text objects in the layer except those to ignore
    For Each entity In modelSpace
        If entity.layer = layerName Then
            If TypeOf entity Is AcadText Then
                If entity.TextString <> ignoreValue Then
                    textObjects.Add entity
                End If
            End If
        End If
    Next entity

    If textObjects.count = 0 Then
        MsgBox "Nenhum texto encontrado na camada selecionada.", vbInformation
        Exit Sub
    End If

    ' 3. Store text and reference for sorting
    ReDim textData(1 To textObjects.count, 1 To 2)
    For i = 1 To textObjects.count
        Set textObj = textObjects(i)
        textData(i, 1) = textObj.TextString
        Set textData(i, 2) = textObj
    Next i

    ' 4. Sort textData alphabetically by text string (simple bubble sort)
    For i = 1 To UBound(textData, 1) - 1
        For j = i + 1 To UBound(textData, 1)
            If StrComp(textData(i, 1), textData(j, 1), vbTextCompare) > 0 Then
                temp = textData(i, 1): textData(i, 1) = textData(j, 1): textData(j, 1) = temp
                Set temp = textData(i, 2): Set textData(i, 2) = textData(j, 2): Set textData(j, 2) = temp
            End If
        Next j
    Next i

    ' 5. Create/find layer "Index" and set color to red (1)
    foundIndexLayer = False
    For Each indexLayer In acadDoc.layers
        If indexLayer.name = "Index" Then
            foundIndexLayer = True
            Exit For
        End If
    Next indexLayer
    If Not foundIndexLayer Then
        Set indexLayer = acadDoc.layers.Add("Index")
    End If
    indexLayer.Color = 1 ' Red

    ' 6. Count occurrences of each text value before adding index texts
    Dim dict As Object
    Dim txt As Variant
    Dim eqCount As Long
    Set dict = CreateObject("Scripting.Dictionary")
    For i = 1 To UBound(textData, 1)
        txt = textData(i, 1)
        If dict.Exists(txt) Then
            dict(txt) = dict(txt) + 1
        Else
            dict(txt) = 1
        End If
    Next i

    ' 7. Add index text to the left of each sorted text object
    ' Create index numbering that repeats for identical texts
    Dim currentIndex As Long
    currentIndex = 1
    
    For i = 1 To UBound(textData, 1)
        Set textObj = textData(i, 2)
        
        ' If this is not the first item and text is different from previous, increment index
        If i > 1 Then
            If textData(i, 1) <> textData(i - 1, 1) Then
                currentIndex = currentIndex + 1
            End If
        End If
        
        indexValue = CStr(currentIndex)
        indexHeight = 8 * textObj.height
        offsetX = -20 * textObj.height ' 12x height to the left
        Dim insPt As Variant
        insPt = textObj.InsertionPoint
        indexPoint(0) = insPt(0) + offsetX
        indexPoint(1) = insPt(1)
        indexPoint(2) = insPt(2)
        Set indexText = modelSpace.AddText(indexValue, indexPoint, indexHeight)
        indexText.layer = "Index"
        ' Green (3) for repeated values, red (1) for unique values
        If dict(textData(i, 1)) > 1 Then
            indexText.Color = 3 ' Green - repeated value
        Else
            indexText.Color = 1 ' Red - unique value
        End If
        indexText.Update
    Next i

    acadDoc.Regen acAllViewports

    eqCount = 0
    For Each txt In dict.Keys
        If dict(txt) > 1 Then eqCount = eqCount + dict(txt)
    Next
    
    Dim uniqueCount As Long
    uniqueCount = dict.count

    MsgBox "Indexação concluída com sucesso." & vbCrLf & _
           "Quantidade de textos iguais encontrados: " & eqCount & vbCrLf & _
           "Valores únicos: " & uniqueCount, vbInformation
End Sub

Attribute VB_Name = "M_autoOrient"
Option Explicit

' Auto-orient a selection by finding the best rotation angle (0-180 degrees).
' Call from form with: AutoOrientFromForm(Me)
' Call standalone with: AutoOrient()

Private Type Point2D
    X As Double
    Y As Double
End Type

Public Sub AutoOrient()
    AutoOrientCore Nothing
End Sub

Public Sub AutoOrientFromForm(frm As Object)
    AutoOrientCore frm
End Sub

Private Sub AutoOrientCore(frm As Object)
    Dim doc As AcadDocument
    Set doc = ThisDrawing
    
    Dim wasVisible As Boolean: wasVisible = False
    If Not frm Is Nothing Then
        On Error Resume Next
        wasVisible = frm.Visible
        frm.Hide
        On Error GoTo 0
    End If
    
    On Error GoTo ErrorHandler
    
    ' Prompt user to select entities
    Dim ss As AcadSelectionSet
    Set ss = doc.SelectionSets.Add("AUTOORIENT_SS")
    
    doc.Utility.prompt vbCr & "Selecione os objetos: " & vbCr
    ss.SelectOnScreen
    
    If ss.count = 0 Then
        doc.Utility.prompt "Nenhum objeto selecionado." & vbCr
        ss.Delete
        GoTo Cleanup
    End If
    
    doc.StartUndoMark
    
    ' Get bounding box of current selection
    Dim minPt As Variant, maxPt As Variant
    GetSelectionBounds ss, minPt, maxPt
    
    Dim centerPt(0 To 2) As Double
    centerPt(0) = (minPt(0) + maxPt(0)) / 2
    centerPt(1) = (minPt(1) + maxPt(1)) / 2
    centerPt(2) = 0
    
    ' Find best rotation angle
    Dim bestAngle As Double
    Dim bestHeight As Double
    bestAngle = FindBestRotationAngleInternal(ss, centerPt, bestHeight)
    
    Dim degAngle As Double
    degAngle = bestAngle * 180 / 3.14159265358979
    
    doc.Utility.prompt "Melhor angulo: " & Format(degAngle, "0.00") & " graus" & vbCr
    
    ' Apply rotation if angle is significant
    If Abs(bestAngle) > 0.001 Then
        RotateSelectedEntities ss, centerPt, bestAngle
        MsgBox "Rotacionado em " & Format(degAngle, "0.00") & " graus.", vbInformation
    Else
        MsgBox "Nenhuma rotacao necessaria (angulo ~0).", vbInformation
    End If
    
    doc.EndUndoMark
    ss.Delete
    
Cleanup:
    If Not frm Is Nothing And wasVisible Then
        On Error Resume Next
        frm.Show
        On Error GoTo 0
    End If
    Exit Sub
    
ErrorHandler:
    On Error Resume Next
    If Not ss Is Nothing Then ss.Delete
    MsgBox "Erro: " & Err.Description, vbCritical
    If Not frm Is Nothing And wasVisible Then frm.Show
End Sub

' Get bounding box of all entities in selection set
Private Sub GetSelectionBounds(ss As AcadSelectionSet, ByRef minPt As Variant, ByRef maxPt As Variant)
    Dim minX As Double, minY As Double, maxX As Double, maxY As Double
    Dim first As Boolean: first = True
    
    Dim ent As AcadEntity
    Dim entMinPt As Variant, entMaxPt As Variant
    
    For Each ent In ss
        On Error Resume Next
        ent.GetBoundingBox entMinPt, entMaxPt
        
        If Not first Then
            If entMinPt(0) < minX Then minX = entMinPt(0)
            If entMinPt(1) < minY Then minY = entMinPt(1)
            If entMaxPt(0) > maxX Then maxX = entMaxPt(0)
            If entMaxPt(1) > maxY Then maxY = entMaxPt(1)
        Else
            minX = entMinPt(0)
            minY = entMinPt(1)
            maxX = entMaxPt(0)
            maxY = entMaxPt(1)
            first = False
        End If
        On Error GoTo 0
    Next ent
    
    minPt = Array(minX, minY, 0)
    maxPt = Array(maxX, maxY, 0)
End Sub

' Find best rotation angle by testing increments from 0 to 180 degrees
Private Function FindBestRotationAngleInternal(ss As AcadSelectionSet, centerPt() As Double, ByRef heightOut As Double) As Double
    Const STEP_DEG As Double = 1
    Const PI As Double = 3.14159265358979
    
    ' Gather all sampling points relative to centerPt ONCE
    Dim points() As Point2D
    Dim numPoints As Long
    numPoints = CollectSamplingPoints(ss, centerPt, points)
    
    Dim bestAngle As Double: bestAngle = 0
    Dim bestHeight As Double: bestHeight = 1E+30
    Dim bestAspect As Double: bestAspect = 0
    
    Dim angle As Double
    Dim deg As Double
    Dim width As Double, height As Double, aspect As Double
    
    ' Test angles from 0 to 180 degrees
    For deg = 0 To 180 Step STEP_DEG
        angle = deg * PI / 180
        
        ' Get bounds from pre-collected points rotated by angle
        GetRotatedBoundsFromPoints points, numPoints, angle, width, height
        
        If height > 0 Then
            aspect = width / height
        Else
            aspect = 0
        End If
        
        ' Prefer smaller height; use aspect ratio as tiebreaker
        If height < bestHeight - 0.001 Or (Abs(height - bestHeight) < 0.001 And aspect > bestAspect) Then
            bestHeight = height
            bestAspect = aspect
            bestAngle = angle
        End If
    Next deg
    
    heightOut = bestHeight
    FindBestRotationAngleInternal = bestAngle
End Function

Private Function CollectSamplingPoints(ss As AcadSelectionSet, centerPt() As Double, ByRef pointsOut() As Point2D) As Long
    Dim ent As AcadEntity
    Dim count As Long: count = 0
    ReDim pointsOut(0 To 1000) As Point2D
    
    For Each ent In ss
        If IsExcludedFromAngleCalculation(ent) Then
            GoTo NextEntity
        End If

        Dim objName As String
        objName = UCase$(ent.ObjectName)
        
        ' For Polylines, explode to get accurate geometry (lines and arcs)
        If InStr(1, objName, "POLYLINE", vbTextCompare) > 0 Then
            CollectPolylinePoints ent, centerPt, pointsOut, count
        ElseIf InStr(1, objName, "REGION", vbTextCompare) > 0 Then
            CollectRegionPoints ent, centerPt, pointsOut, count
        ElseIf objName = "ACDBLINE" Or objName = "ACADLINE" Then
            CollectLinePoints ent, centerPt, pointsOut, count
        ElseIf objName = "ACDBARC" Or objName = "ACADARC" Then
            CollectArcPoints ent, centerPt, pointsOut, count
        Else
            ' Fallback to bounding box corners for other entities
            CollectBoundingBoxPoints ent, centerPt, pointsOut, count
        End If

NextEntity:
    Next ent
    
    CollectSamplingPoints = count
End Function

Private Function IsExcludedFromAngleCalculation(ent As AcadEntity) As Boolean
    Dim objName As String
    objName = UCase$(ent.ObjectName)
    
    If InStr(1, objName, "REGION", vbTextCompare) > 0 Then
        IsExcludedFromAngleCalculation = True
        Exit Function
    End If
    
    Dim layerName As String
    layerName = UCase$(Trim$(ent.layer))
    
    If layerName = "SHAPES" Then
        IsExcludedFromAngleCalculation = True
        Exit Function
    End If
    
    IsExcludedFromAngleCalculation = False
End Function

Private Sub AddPoint(X As Double, Y As Double, ByRef points() As Point2D, ByRef count As Long)
    If count > UBound(points) Then
        ReDim Preserve points(0 To UBound(points) * 2) As Point2D
    End If
    points(count).X = X
    points(count).Y = Y
    count = count + 1
End Sub

Private Sub CollectRegionPoints(ent As AcadEntity, centerPt() As Double, ByRef points() As Point2D, ByRef count As Long)
    On Error Resume Next
    Dim exploded As Variant
    exploded = ent.Explode
    
    If Err.Number <> 0 Or IsEmpty(exploded) Then
        Err.Clear
        CollectBoundingBoxPoints ent, centerPt, points, count
        Exit Sub
    End If
    
    Dim i As Long
    Dim subEnt As AcadEntity
    ' For regions, sometimes Explode returns a Region again (if complex) or the boundary curves.
    ' If it's a set of lines/arcs, we process them.
    ' If it's just a Region, likely identical, we must avoid infinite recursion.
    ' We iterate and check types.
    For i = LBound(exploded) To UBound(exploded)
        Set subEnt = exploded(i)
        Dim subName As String
        subName = UCase$(subEnt.ObjectName)
        
        If InStr(1, subName, "REGION", vbTextCompare) > 0 Then
            ' If explode returned another region, try exploding THAT one level deeper
            ' Often regions explode into 1 region if created from closed loop?
            ' Actually, Exploding a Region should yield Lines/Arcs/Splines.
            ' But just in case, use centroid/bbox for sub-region to be safe
            CollectBoundingBoxPoints subEnt, centerPt, points, count
        ElseIf InStr(1, subName, "LINE", vbTextCompare) > 0 Then
            CollectLinePoints subEnt, centerPt, points, count
        ElseIf InStr(1, subName, "ARC", vbTextCompare) > 0 Then
            CollectArcPoints subEnt, centerPt, points, count
        Else
            CollectBoundingBoxPoints subEnt, centerPt, points, count
        End If
        
        subEnt.Delete
    Next i
    On Error GoTo 0
End Sub

Private Sub CollectPolylinePoints(ent As AcadEntity, centerPt() As Double, ByRef points() As Point2D, ByRef count As Long)
    On Error Resume Next
    Dim exploded As Variant
    exploded = ent.Explode
    
    If Err.Number <> 0 Or IsEmpty(exploded) Then
        Err.Clear
        CollectBoundingBoxPoints ent, centerPt, points, count
        Exit Sub
    End If
    
    Dim i As Long
    Dim subEnt As AcadEntity
    For i = LBound(exploded) To UBound(exploded)
        Set subEnt = exploded(i)
        
        Dim subName As String
        subName = UCase$(subEnt.ObjectName)
        
        If InStr(1, subName, "LINE", vbTextCompare) > 0 Then
            CollectLinePoints subEnt, centerPt, points, count
        ElseIf InStr(1, subName, "ARC", vbTextCompare) > 0 Then
            CollectArcPoints subEnt, centerPt, points, count
        Else
            CollectBoundingBoxPoints subEnt, centerPt, points, count
        End If
        
        subEnt.Delete
    Next i
    On Error GoTo 0
End Sub

Private Sub CollectLinePoints(lineEnt As AcadEntity, centerPt() As Double, ByRef points() As Point2D, ByRef count As Long)
    On Error Resume Next
    Dim StartPt As Variant, EndPt As Variant
    StartPt = lineEnt.startPoint
    EndPt = lineEnt.endPoint
    
    AddPoint StartPt(0) - centerPt(0), StartPt(1) - centerPt(1), points, count
    AddPoint EndPt(0) - centerPt(0), EndPt(1) - centerPt(1), points, count
    On Error GoTo 0
End Sub

Private Sub CollectArcPoints(arcEnt As AcadEntity, centerPt() As Double, ByRef points() As Point2D, ByRef count As Long)
    On Error Resume Next
    Dim StartPt As Variant, EndPt As Variant
    StartPt = arcEnt.startPoint
    EndPt = arcEnt.endPoint
    
    AddPoint StartPt(0) - centerPt(0), StartPt(1) - centerPt(1), points, count
    AddPoint EndPt(0) - centerPt(0), EndPt(1) - centerPt(1), points, count
    
    ' Sample midpoint of arc
    Dim radius As Double, center As Variant, startAngle As Double, endAngle As Double
    radius = arcEnt.radius
    center = arcEnt.center
    startAngle = arcEnt.startAngle
    endAngle = arcEnt.endAngle
    
    ' Normalize angles for arc span calculation
    ' BricsCAD/AutoCAD arcs are CCW
    
    Dim angleDiff As Double
    angleDiff = endAngle - startAngle
    If angleDiff <= 0 Then angleDiff = angleDiff + 6.28318530717959
    
    Dim midAngle As Double
    midAngle = startAngle + (angleDiff / 2)
    
    Dim midX As Double, midY As Double
    midX = center(0) + radius * Cos(midAngle)
    midY = center(1) + radius * Sin(midAngle)
    
    AddPoint midX - centerPt(0), midY - centerPt(1), points, count
    On Error GoTo 0
End Sub

Private Sub CollectSplinePoints(splineEnt As AcadEntity, centerPt() As Double, ByRef points() As Point2D, ByRef count As Long)
    On Error Resume Next
    Dim ctrlPoints As Variant
    Dim numPoints As Long
    Dim i As Long
    
    ' Try to get control points
    ctrlPoints = splineEnt.ControlPoints
    If Err.Number = 0 And Not IsEmpty(ctrlPoints) Then
        numPoints = (UBound(ctrlPoints) - LBound(ctrlPoints) + 1) / 3
        For i = 0 To numPoints - 1
            AddPoint ctrlPoints(i * 3) - centerPt(0), ctrlPoints(i * 3 + 1) - centerPt(1), points, count
        Next i
    Else
        Err.Clear
        ' Fallback to fit points if control points fail
        Dim fitPoints As Variant
        fitPoints = splineEnt.fitPoints
        If Err.Number = 0 And Not IsEmpty(fitPoints) Then
             numPoints = (UBound(fitPoints) - LBound(fitPoints) + 1) / 3
             For i = 0 To numPoints - 1
                 AddPoint fitPoints(i * 3) - centerPt(0), fitPoints(i * 3 + 1) - centerPt(1), points, count
             Next i
        Else
             CollectBoundingBoxPoints splineEnt, centerPt, points, count
        End If
    End If
    On Error GoTo 0
End Sub

Private Sub CollectEllipsePoints(ell As AcadEntity, centerPt() As Double, ByRef points() As Point2D, ByRef count As Long)
    On Error Resume Next
    Dim center As Variant
    Dim majAxis As Variant
    Dim radiusRatio As Double
    Dim startAngle As Double, endAngle As Double
    
    center = ell.center
    majAxis = ell.MajorAxis
    radiusRatio = ell.radiusRatio
    startAngle = ell.startAngle
    endAngle = ell.endAngle
    
    ' Add Start/End/Center
    Dim StartPt As Variant, EndPt As Variant
    StartPt = ell.startPoint
    EndPt = ell.endPoint
    
    AddPoint StartPt(0) - centerPt(0), StartPt(1) - centerPt(1), points, count
    AddPoint EndPt(0) - centerPt(0), EndPt(1) - centerPt(1), points, count
    
    ' Approximate the curve with 8 points along the perimeter
    Dim i As Long
    Dim t As Double
    Dim angleSpan As Double
    
    If endAngle < startAngle Then endAngle = endAngle + 6.28318530717959
    angleSpan = endAngle - startAngle
    
    ' Major axis length
    Dim majLen As Double
    majLen = Sqr(majAxis(0) ^ 2 + majAxis(1) ^ 2)
    
    ' Minor axis length
    Dim minLen As Double
    minLen = majLen * radiusRatio
    
    ' Angle of major axis
    Dim rotAngle As Double
    If majLen > 0.000001 Then
        rotAngle = Atn(majAxis(1) / majAxis(0))
        ' Quadrant fix
        If majAxis(0) < 0 Then rotAngle = rotAngle + 3.14159265358979
    Else
        rotAngle = 0
    End If
    
    Dim cosR As Double: cosR = Cos(rotAngle)
    Dim sinR As Double: sinR = Sin(rotAngle)
    
    For i = 1 To 7
        t = startAngle + (angleSpan * i / 8)
        
        ' Parametric ellipse equation
        Dim pX As Double, pY As Double
        pX = majLen * Cos(t)
        pY = minLen * Sin(t)
        
        ' Rotate to align with major axis
        Dim finalX As Double, finalY As Double
        finalX = center(0) + (pX * cosR - pY * sinR)
        finalY = center(1) + (pX * sinR + pY * cosR)
        
        AddPoint finalX - centerPt(0), finalY - centerPt(1), points, count
    Next i
    
    On Error GoTo 0
End Sub

Private Sub CollectBoundingBoxPoints(ent As AcadEntity, centerPt() As Double, ByRef points() As Point2D, ByRef count As Long)
    On Error Resume Next
    Dim minPt As Variant, maxPt As Variant
    ent.GetBoundingBox minPt, maxPt
    
    If Err.Number = 0 Then
        AddPoint minPt(0) - centerPt(0), minPt(1) - centerPt(1), points, count
        AddPoint maxPt(0) - centerPt(0), minPt(1) - centerPt(1), points, count
        AddPoint maxPt(0) - centerPt(0), maxPt(1) - centerPt(1), points, count
        AddPoint minPt(0) - centerPt(0), maxPt(1) - centerPt(1), points, count
    End If
    On Error GoTo 0
End Sub

Private Sub GetRotatedBoundsFromPoints(points() As Point2D, count As Long, angle As Double, _
    ByRef widthOut As Double, ByRef heightOut As Double)
    
    Const LARGE As Double = 1E+30
    Dim minX As Double: minX = LARGE
    Dim minY As Double: minY = LARGE
    Dim maxX As Double: maxX = -LARGE
    Dim maxY As Double: maxY = -LARGE
    
    Dim cosA As Double: cosA = Cos(angle)
    Dim sinA As Double: sinA = Sin(angle)
    Dim i As Long
    Dim rx As Double, ry As Double
    
    For i = 0 To count - 1
        rx = points(i).X * cosA - points(i).Y * sinA
        ry = points(i).X * sinA + points(i).Y * cosA
        
        If rx < minX Then minX = rx
        If rx > maxX Then maxX = rx
        If ry < minY Then minY = ry
        If ry > maxY Then maxY = ry
    Next i
    
    If minX > maxX Then ' No points processed
        widthOut = 0
        heightOut = 0
    Else
        widthOut = maxX - minX
        heightOut = maxY - minY
    End If
End Sub

' Rotate all entities in the selection set
Private Sub RotateSelectedEntities(ss As AcadSelectionSet, centerPt() As Double, angle As Double)
    Dim ent As AcadEntity
    Dim errCount As Long: errCount = 0
    
    For Each ent In ss
        On Error Resume Next
        ent.Rotate centerPt, angle
        If Err.Number <> 0 Then
            errCount = errCount + 1
            Err.Clear
        End If
        On Error GoTo 0
    Next ent
    
    If errCount > 0 Then
        MsgBox "Aviso: " & errCount & " entidade(s) nao pudo ser rotacionada(s).", vbExclamation
    End If
End Sub

Attribute VB_Name = "M_cellCenters"
Option Explicit

Sub DrawCellCenters()
    ' --- 1. Hide formPerfisul01 ---
    On Error Resume Next
    formPerfisul01.Hide
    On Error GoTo 0
    
    Dim sset As AcadSelectionSet
    Dim ent As AcadEntity
    Dim lineObj As AcadLine
    Dim circ As AcadCircle
    
    ' Arrays to store unique grid coordinates
    Dim xGrid() As Double
    Dim yGrid() As Double
    Dim xCount As Long
    Dim yCount As Long
    
    Dim i As Long, j As Long
    Dim tempVal As Double
    
    ' --- 2. Selection (Area) ---
    On Error Resume Next
    Set sset = ThisDrawing.SelectionSets.item("SS_GridDetection")
    If Err Then
        Err.Clear
        Set sset = ThisDrawing.SelectionSets.Add("SS_GridDetection")
    Else
        sset.Clear
    End If
    On Error GoTo 0
    
    MsgBox "Select area (square selection) covering the grid lines and circles."
    sset.SelectOnScreen
    
    If sset.count = 0 Then
        MsgBox "No objects selected."
        Exit Sub
    End If
    
    ' Initialize dynamic arrays
    ReDim xGrid(0 To 100)
    ReDim yGrid(0 To 100)
    xCount = 0
    yCount = 0
    
    ' --- 3. Filter Selection for Grid Lines ---
    ' Identify vertical and horizontal lines
    Dim sx As Double, sy As Double
    Dim ex As Double, ey As Double
    Dim isVert As Boolean
    Dim isHoriz As Boolean
    
    For Each ent In sset
        If ent.ObjectName = "AcDbLine" Then
            Set lineObj = ent
            sx = lineObj.startPoint(0)
            sy = lineObj.startPoint(1)
            ex = lineObj.endPoint(0)
            ey = lineObj.endPoint(1)
            
            ' Vertical line? (X diff is small)
            If Abs(sx - ex) < 0.1 Then
                AddUniqueVal xGrid, xCount, (sx + ex) / 2
            End If
            
            ' Horizontal line? (Y diff is small)
            If Abs(sy - ey) < 0.1 Then
                AddUniqueVal yGrid, yCount, (sy + ey) / 2
            End If
        End If
    Next ent
    
    ' Validate Grid
    If xCount < 2 Or yCount < 2 Then
        MsgBox "Could not detect a grid. Found " & xCount & " vertical lines and " & yCount & " horizontal lines." & vbCrLf & "Please select the grid lines representing rows and columns."
        sset.Delete
        Exit Sub
    End If
    
    ' --- 4. Sort Coordinates ---
    ' We need sorted coordinates to define intervals (cells)
    SortDoubles xGrid, xCount
    SortDoubles yGrid, yCount
    
    ' --- 5. Ensure "Shapes" Layer Exists ---
    Dim shapesLayer As AcadLayer
    Dim layerExists As Boolean
    layerExists = False
    For Each shapesLayer In ThisDrawing.layers
        If UCase(shapesLayer.name) = "SHAPES" Then
            layerExists = True
            Exit For
        End If
    Next
    If Not layerExists Then
        Set shapesLayer = ThisDrawing.layers.Add("Shapes")
          shapesLayer.Color = acGreen
    Else
        Set shapesLayer = ThisDrawing.layers("Shapes")
    End If

    ' --- 6. Process Circles ---
    ' Iterate circles. Find which cell (interval) they fall into.
    ' Calculate center of that cell.
    
    Dim cx As Double, cy As Double
    Dim cellLeft As Double, cellRight As Double
    Dim cellBottom As Double, cellTop As Double
    Dim cellCenterX As Double, cellCenterY As Double
    Dim pt(0 To 2) As Double
    Dim pointObj As AcadPoint
    
    Dim matchCount As Long
    matchCount = 0
    
    ' Arrays to track unique columns/rows based on processed circles
    Dim circleCols() As Double
    Dim circleRows() As Double
    Dim circleColCount As Long
    Dim circleRowCount As Long
    ReDim circleCols(0 To 100)
    ReDim circleRows(0 To 100)
    circleColCount = 0
    circleRowCount = 0
    
    ' We need to loop through the selection again to find circles
    For Each ent In sset
        If ent.ObjectName = "AcDbCircle" Then
            Set circ = ent
            cx = circ.center(0)
            cy = circ.center(1)
            
            ' Find X Interval (Column)
            Dim foundX As Boolean
            foundX = False
            cellLeft = 0
            cellRight = 0
            
            For i = 0 To xCount - 2
                ' Check if circle X is between vertical lines i and i+1
                ' Add a small tolerance just in case circle is ON the line (unlikely for center)
                If cx >= xGrid(i) - 0.1 And cx <= xGrid(i + 1) + 0.1 Then
                    cellLeft = xGrid(i)
                    cellRight = xGrid(i + 1)
                    foundX = True
                    Exit For
                End If
            Next i
            
            ' Find Y Interval (Row)
            Dim foundY As Boolean
            foundY = False
            cellBottom = 0
            cellTop = 0
            
            For j = 0 To yCount - 2
                ' Check if circle Y is between horizontal lines j and j+1
                If cy >= yGrid(j) - 0.1 And cy <= yGrid(j + 1) + 0.1 Then
                    cellBottom = yGrid(j)
                    cellTop = yGrid(j + 1)
                    foundY = True
                    Exit For
                End If
            Next j
            
            ' If found both, we have the cell!
            If foundX And foundY Then
                cellCenterX = (cellLeft + cellRight) / 2
                cellCenterY = (cellBottom + cellTop) / 2
                
                ' Track unique columns and rows from circles (not from line count)
                AddUniqueVal circleCols, circleColCount, cellCenterX
                AddUniqueVal circleRows, circleRowCount, cellCenterY
                
                ' Add Point at geometric center of the detected cell
                pt(0) = cellCenterX
                pt(1) = cellCenterY
                pt(2) = 0
                
                Set pointObj = ThisDrawing.modelSpace.AddPoint(pt)
                pointObj.layer = "Shapes"
                pointObj.Color = acByLayer
                     pointObj.Linetype = "Continuous"
                
                matchCount = matchCount + 1
            End If
            
        End If
    Next ent
    
    ' Count active rows and cols
    Dim validCols As Long, validRows As Long
    validCols = circleColCount
    validRows = circleRowCount
    
    sset.Delete
    MsgBox "Process Complete." & vbCrLf & _
           "Defined Grid (with circles): " & validCols & " cols x " & validRows & " rows." & vbCrLf & _
           "Centers Created: " & matchCount
           
End Sub

' --- Helper: Add unique value to array with tolerance ---
Sub AddUniqueVal(ByRef arr() As Double, ByRef count As Long, val As Double)
    Dim i As Long
    ' Check if exists
    For i = 0 To count - 1
        If Abs(arr(i) - val) < 0.1 Then Exit Sub ' Tolerance 0.1
    Next i
    
    ' Resize if needed (chunk allocation)
    If count > UBound(arr) Then
        ReDim Preserve arr(UBound(arr) + 50)
    End If
    
    arr(count) = val
    count = count + 1
End Sub

' --- Helper: Bubble Sort for Double Array ---
Sub SortDoubles(ByRef arr() As Double, count As Long)
    Dim i As Long, j As Long
    Dim temp As Double
    ' Only sort the valid portion (0 to count-1)
    For i = 0 To count - 2
        For j = i + 1 To count - 1
            If arr(i) > arr(j) Then
                temp = arr(i)
                arr(i) = arr(j)
                arr(j) = temp
            End If
        Next j
    Next i
End Sub

Attribute VB_Name = "M_detectShapes"
Option Explicit

' ------------------------------------------------------------------------------
' Module: detectShapes.vba
' Description: Performs Topological Data Analysis to detect outer boundaries
'              within a user selection and highlights them.
' Usage: Called from formPerfisul01
' ------------------------------------------------------------------------------

Public Sub DetectOuterShapes()
    ' 1. Hide the userform
    On Error Resume Next
    formPerfisul01.Hide
    On Error GoTo 0
    
    Dim doc As AcadDocument
    Set doc = ThisDrawing
    
    ' Ensure "Shapes" layer exists
    Dim shapesLayer As AcadLayer
    On Error Resume Next
    Set shapesLayer = doc.layers.item("Shapes")
    If Err.Number <> 0 Then
        Set shapesLayer = doc.layers.Add("Shapes")
        shapesLayer.Color = acGreen
    End If
    On Error GoTo 0
    
    ' 2. Prompt for area selection
    ' We use a selection set to gather objects
    Dim sset As AcadSelectionSet
    On Error Resume Next
        Set sset = doc.SelectionSets.item("TDA_SELECTION")
        If Err.Number = 0 Then
            sset.Delete
        End If
        Err.Clear
    On Error GoTo 0
    
    Set sset = doc.SelectionSets.Add("TDA_SELECTION")
    
    ' Prompt via command line
    doc.Utility.prompt vbCrLf & "Select objects for Outer Shape Detection (Window Selection recommended)..." & vbCrLf
    
    ' Allow user to select objects
    ' Filter for curves that can form regions: Lines, Arcs, Circles, Polylines, Splines, Ellipses
    Dim gpCode(0) As Integer
    Dim dataValue(0) As Variant
    gpCode(0) = 0
    dataValue(0) = "LINE,ARC,CIRCLE,LWPOLYLINE,POLYLINE,SPLINE,ELLIPSE"
    
    On Error Resume Next
    sset.SelectOnScreen gpCode, dataValue
    If sset.count = 0 Then
        MsgBox "Selection canceled or no valid objects selected.", vbExclamation
        If Not formPerfisul01 Is Nothing Then formPerfisul01.Show
        Exit Sub
    End If
    On Error GoTo 0
    
    ' 3. Topological Data Analysis (Outer Shape Detection)
    ' Strategy:
    ' 1. Attempt to create Regions from the selection. This automatically finds closed loops.
    ' 2. Regions effectively represent the topology. Use boolean logic to find parent loops.
    '    A "Parent" or "Outer" loop is one that is NOT contained within any other region in the set.
    
    ' Collect objects for AddRegion
    Dim objs() As Object
    ReDim objs(sset.count - 1)
    Dim i As Integer
    For i = 0 To sset.count - 1
        Set objs(i) = sset.item(i)
    Next i
    
    ' Create Regions
    ' Note: AddRegion might fail if curves don't form closed loops.
    ' It returns a Variant containing an array of Region objects.
    Dim createdRegions As Variant
    On Error Resume Next
    createdRegions = doc.modelSpace.AddRegion(objs)
    If Err.Number <> 0 Then
        MsgBox "Failed to create regions. Ensure selected objects form closed loops.", vbCritical
        If Not formPerfisul01 Is Nothing Then formPerfisul01.Show
        Exit Sub
    End If
    On Error GoTo 0
    
    If IsEmpty(createdRegions) Then
        MsgBox "No closed regions could be detected from selection.", vbExclamation
        If Not formPerfisul01 Is Nothing Then formPerfisul01.Show
        Exit Sub
    End If
    
    ' Store regions in an array for easier handling
    ' We need to cast the Variant array to something strictly typed or just iterate
    Dim regionList() As AcadRegion
    Dim rCount As Integer
    rCount = UBound(createdRegions) - LBound(createdRegions) + 1
    ReDim regionList(rCount - 1)
    
    Dim r As Variant
    Dim idx As Integer
    idx = 0
    For Each r In createdRegions
        Set regionList(idx) = r
        idx = idx + 1
    Next r
    
    ' Sort regionList by Area Descending (Bubble Sort)
    ' This optimization helps because a region can only be inside a LARGER region.
    Dim tempReg As AcadRegion
    Dim sorted As Boolean
    Dim j As Integer
    sorted = False
    While Not sorted
        sorted = True
        For i = 0 To UBound(regionList) - 1
            If regionList(i).area < regionList(i + 1).area Then
                Set tempReg = regionList(i)
                Set regionList(i) = regionList(i + 1)
                Set regionList(i + 1) = tempReg
                sorted = False
            End If
        Next i
    Wend
    
    ' Identify Outer Shapes
    Dim isInner As Boolean
    Dim k As Integer
    Dim testReg As AcadRegion
    Dim containerReg As AcadRegion
    Dim copyTest As AcadRegion
    Dim copyContainer As AcadRegion
    Dim intersectionReg As AcadRegion
    
    ' Track which regions to delete (inner ones)
    ' We valid flags to avoid accessing deleted objects
    Dim regionsToDelete() As Boolean
    ReDim regionsToDelete(UBound(regionList))
    
    doc.Utility.prompt "Analyzing " & rCount & " detected regions..." & vbCrLf
    
    For i = 0 To UBound(regionList)
        regionsToDelete(i) = False
    Next i
    
    For i = 0 To UBound(regionList)
        Set testReg = regionList(i)
        isInner = False
        
        ' Compare against other regions to see if 'testReg' is inside 'containerReg'
        For k = 0 To UBound(regionList)
            If i <> k Then
                ' Optimization: If container is already marked as inner,
                ' can it still contain others? Yes, nesting (A > B > C).
                ' If B is inside A, B is marked to delete.
                ' C is inside B. We check C vs B. B is still a valid object until we delete it later.
                ' Comparison is safe.
                
                Set containerReg = regionList(k)
                
                ' Only check if container is larger (or equal)
                If containerReg.area >= testReg.area Then
                     
                    ' Check containment: Intersection(Test, Container) == Test
                    ' Use Copys to avoid altering originals
                    Set copyTest = testReg.Copy()
                    Set copyContainer = containerReg.Copy()
                    
                    On Error Resume Next
                    ' Boolean(acIntersection, object) modifies the object calling the method
                    copyTest.Boolean acIntersection, copyContainer
                    
                    If Err.Number = 0 Then
                         ' Check if area matches original area
                         If Abs(copyTest.area - testReg.area) < 0.0001 Then
                             ' It is inside!
                             isInner = True
                             
                             ' Clean up copies
                             copyTest.Delete
                             copyContainer.Delete
                             Exit For
                         End If
                    End If
                    On Error GoTo 0
                    
                    ' Clean up copies
                    If Not copyTest Is Nothing Then
                        On Error Resume Next
                        copyTest.Delete
                    End If
                    If Not copyContainer Is Nothing Then
                        On Error Resume Next
                        copyContainer.Delete
                    End If
                    On Error GoTo 0
                End If
            End If
        Next k
        
        If isInner Then
            ' Mark it as a child / hole
            regionsToDelete(i) = True
        Else
            ' It is a Parent / Outer Shape
            ' Start highlighting process but don't delete yet
        End If
    Next i
    
    ' Now process results
    For i = 0 To UBound(regionList)
        If regionsToDelete(i) Then
            ' It was inner - delete it
             On Error Resume Next
             regionList(i).Delete
             On Error GoTo 0
        Else
            ' It is a Parent / Outer Shape
            Set testReg = regionList(i)
            testReg.layer = "Shapes"
            testReg.Color = acByLayer
            On Error Resume Next
            testReg.Linetype = "Continuous"
            On Error GoTo 0
            testReg.Highlight False
        End If
    Next i
    
    doc.Utility.prompt "Analysis Complete. Outer shapes moved to layer 'Shapes' and highlighted in GREEN." & vbCrLf
    ' MsgBox "Analysis Complete. Outer shapes moved to layer 'Shapes' and highlighted.", vbInformation
    
    ' Show userform again
    If Not formPerfisul01 Is Nothing Then formPerfisul01.Show

End Sub

Attribute VB_Name = "M_distributeShapesToGrid"
Option Explicit

Private Declare PtrSafe Function GetSystemMetrics Lib "user32" (ByVal nIndex As Long) As Long
Private Const SM_CXSCREEN = 0

' Distribute detected shapes onto a grid of cells.
' Steps:
' 1) Hide formPerfisul01 and ask user to window-select the shapes.
' 2) Detect closed regions from the selection (outer shapes only).
' 3) For each region, gather its entities, auto-orient to minimize height, and record width/height.
' 4) Get the maximum region width (maxWidth).
' 5) Ask user to select the grid; detect columns, rows, cell width/height, and centers.
' 6) Scale shapes so the widest shape fits the grid cell width.
' 7) Move each rotated/scaled shape to successive cell centers. If shapes exceed cells, create extra rows beneath the grid.

Private Type Point2D
    X As Double
    Y As Double
End Type

Public Sub DistributeShapesToGrid()
    On Error GoTo ErrHandler
    If Not formPerfisul01 Is Nothing Then
        On Error Resume Next
        formPerfisul01.Hide
        On Error GoTo ErrHandler
    End If
    
    Dim doc As AcadDocument
    Set doc = ThisDrawing
    doc.StartUndoMark
    Dim shapesLayer As AcadLayer
    Set shapesLayer = EnsureShapesLayer(doc)
    
    Dim shapeSS As AcadSelectionSet
    Set shapeSS = PrepareSelectionSet(doc, "DSG_SHAPES")
    doc.Utility.prompt vbCr & "Selecione as formas (window selection)..." & vbCr
    MsgBox "Selecione as formas a serem distribuídas.", vbInformation, "Distribuir Formas"
    shapeSS.SelectOnScreen
    If shapeSS.count = 0 Then
        MsgBox "Nenhum objeto selecionado para distribuir.", vbExclamation, "Distribuir Formas"
        GoTo Cleanup
    End If
    NormalizeSelectedLayers shapeSS
    
    Dim allRegions As collection
    Dim outerRegions As collection
    Set outerRegions = DetectOuterRegionsFromSelection(doc, shapeSS, allRegions)
    If outerRegions Is Nothing Or outerRegions.count = 0 Then
        MsgBox "Não foi possível detectar regiões fechadas.", vbExclamation, "Distribuir Formas"
        GoTo Cleanup
    End If
    
    Dim regionEntities As collection
    Set regionEntities = New collection
    Dim regionLabels() As String
    Dim regionCenters() As Variant
    Dim regionWidths() As Double
    Dim regionHeights() As Double
    ReDim regionCenters(1 To outerRegions.count)
    ReDim regionWidths(1 To outerRegions.count)
    ReDim regionHeights(1 To outerRegions.count)
    ReDim regionLabels(1 To outerRegions.count)
    
    ' Read orientation mode from formPerfisul01 option buttons:
    '   0 = Horizontal (maximize width), 1 = Vertical (maximize height), 2 = Diagonal
    Dim orientMode As Integer
    orientMode = 0
    On Error Resume Next
    If formPerfisul01.optOrientVertical.Value Then orientMode = 1
    If formPerfisul01.optOrientDiagonal.Value Then orientMode = 2
    On Error GoTo ErrHandler

    Dim i As Long
    Dim maxWidth As Double: maxWidth = 0
    Dim maxHeight As Double: maxHeight = 0
    
    For i = 1 To outerRegions.count
        Dim reg As AcadRegion
        Set reg = outerRegions(i)
        
        Dim ents As collection
        Set ents = CollectEntitiesForRegion(reg, shapeSS, allRegions)
        regionEntities.Add ents
        regionLabels(i) = ExtractRegionLabel(ents)
        
        Dim centerPt() As Double
        centerPt = GetEntitySetCenter(reg)
        regionCenters(i) = centerPt
        
        Dim minPt As Variant, maxPt As Variant
        If orientMode = 2 Then
            ' Diagonal: defer rotation until after grid is detected (cell dimensions needed)
            GetEntitiesBounds ents, minPt, maxPt
        Else
            Dim bestDim As Double
            Dim bestAngle As Double
            bestAngle = FindBestRotationAngleForEntities(ents, centerPt, bestDim, (orientMode = 1))
            If Abs(bestAngle) > 0.001 Then
                RotateEntities ents, centerPt, bestAngle
            End If
            GetEntitiesBounds ents, minPt, maxPt
        End If
        regionWidths(i) = maxPt(0) - minPt(0)
        regionHeights(i) = maxPt(1) - minPt(1)
        If regionWidths(i) > maxWidth Then maxWidth = regionWidths(i)
        If regionHeights(i) > maxHeight Then maxHeight = regionHeights(i)
    Next i

    ' Sort regions so labeled shapes go first (alphabetical), followed by unlabeled ones
    Set regionEntities = OrderRegionsByLabel(regionEntities, regionLabels)
    
    Dim centers As collection
    Dim cellWidth As Double, cellHeight As Double
    Dim xGrid() As Double, yGrid() As Double
    Dim gridMinX As Double, gridMinY As Double
    Dim gridMaxX As Double, gridMaxY As Double
    Dim zoomMaxX As Double, zoomMaxY As Double
    Dim hasGridTopRight As Boolean
    Dim cols As Long, rows As Long
    Dim gridSS As AcadSelectionSet
    Set centers = New collection
    If Not DetectGridFromUserSelection(centers, cellWidth, cellHeight, xGrid, yGrid, cols, rows, gridSS, _
        gridMinX, gridMinY, gridMaxX, gridMaxY, zoomMaxX, zoomMaxY, hasGridTopRight, outerRegions.count) Then
        GoTo Cleanup
    End If
    
    ' Diagonal orientation: rotate each shape so its bounding-box diagonal matches the cell diagonal,
    ' then recompute maxWidth/maxHeight with the rotated bounds.
    If orientMode = 2 Then
        Const PI_DIAG As Double = 3.14159265358979
        Dim cellDiagAngle As Double
        If cellWidth > 0 Then
            cellDiagAngle = Atn(cellHeight / cellWidth)
        Else
            cellDiagAngle = PI_DIAG / 2
        End If
        maxWidth = 0
        maxHeight = 0
        Dim j As Long
        For j = 1 To regionEntities.count
            Dim diagEnts As collection
            Set diagEnts = regionEntities(j)
            Dim dBmin As Variant, dBmax As Variant
            GetEntitiesBounds diagEnts, dBmin, dBmax
            Dim diagCenter(0 To 2) As Double
            diagCenter(0) = (dBmin(0) + dBmax(0)) / 2
            diagCenter(1) = (dBmin(1) + dBmax(1)) / 2
            diagCenter(2) = 0
            Dim diagAngle As Double
            diagAngle = FindDiagonalRotationAngleForEntities(diagEnts, diagCenter, cellDiagAngle)
            If Abs(diagAngle) > 0.001 Then
                RotateEntities diagEnts, diagCenter, diagAngle
            End If
            Dim dMinPt As Variant, dMaxPt As Variant
            GetEntitiesBounds diagEnts, dMinPt, dMaxPt
            Dim dW As Double, dH As Double
            dW = dMaxPt(0) - dMinPt(0)
            dH = dMaxPt(1) - dMinPt(1)
            If dW > maxWidth Then maxWidth = dW
            If dH > maxHeight Then maxHeight = dH
        Next j
    End If

    If maxWidth <= 0 Or cellWidth <= 0 Then
        MsgBox "Falha ao calcular larguras.", vbExclamation, "Distribuir Formas"
        GoTo Cleanup
    End If

    ' Ask user if they want to fill cell headers with shape labels
    Dim fillHeaders As Boolean
    fillHeaders = (MsgBox("Deseja preencher os cabeçalhos das células com os rótulos das formas?", _
                        vbYesNo + vbQuestion, "Distribuir Formas") = vbYes)
    
    ' Padding factors to leave extra room inside each cell; adjust independently to fine-tune fit.
    Dim widthPaddingFactor As Double
    widthPaddingFactor = 1.08
    Dim heightPaddingFactor As Double
    heightPaddingFactor = 1.2
    Dim scaleFactor As Double
    If orientMode = 1 Then
        ' Vertical: scale so the tallest region fits cell height (using effective body area)
        Const CELL_BODY_RATIO_V As Double = 1
        Dim effectiveCellHeightV As Double
        effectiveCellHeightV = cellHeight * CELL_BODY_RATIO_V
        If maxHeight > 0 And effectiveCellHeightV > 0 Then
            scaleFactor = (maxHeight / effectiveCellHeightV) * heightPaddingFactor
        Else
            scaleFactor = 1
        End If
    ElseIf orientMode = 2 Then
        ' Diagonal: scale grid so the cell contains the shape in both dimensions;
        ' use whichever axis is the binding constraint.
        Dim scaleByW As Double, scaleByH As Double
        scaleByW = (maxWidth / cellWidth) * widthPaddingFactor
        scaleByH = (maxHeight / cellHeight) * heightPaddingFactor
        scaleFactor = IIf(scaleByW > scaleByH, scaleByW, scaleByH)
    Else
        ' Horizontal: scale so the widest region fits cell width
        scaleFactor = (maxWidth / cellWidth) * widthPaddingFactor
    End If
    
    ' Visualize grid centers BEFORE scaling (yellow points for debugging)
    VisualizeGridCenters doc, centers, xGrid, acYellow, "Antes da Escala"
    
    ' Hide Shapes layer before zooming
    On Error Resume Next
    If Not shapesLayer Is Nothing Then shapesLayer.LayerOn = False
    Err.Clear
    On Error GoTo ErrHandler
    
    If scaleFactor > 0.000001 Then
        Dim origin(0 To 2) As Double
        Dim gridMin As Variant, gridMax As Variant
        GetSelectionSetBounds gridSS, gridMin, gridMax
        origin(0) = gridMin(0)
        origin(1) = gridMin(1)
        origin(2) = 0
        ScaleEntitiesInSelection gridSS, origin, scaleFactor
        ScaleGridData xGrid, yGrid, origin, scaleFactor
        gridMinX = origin(0) + (gridMinX - origin(0)) * scaleFactor
        gridMinY = origin(1) + (gridMinY - origin(1)) * scaleFactor
        gridMaxX = origin(0) + (gridMaxX - origin(0)) * scaleFactor
        gridMaxY = origin(1) + (gridMaxY - origin(1)) * scaleFactor
        zoomMaxX = origin(0) + (zoomMaxX - origin(0)) * scaleFactor
        zoomMaxY = origin(1) + (zoomMaxY - origin(1)) * scaleFactor
        cellWidth = AverageStep(xGrid)
        cellHeight = AverageStep(yGrid)
        RebuildCentersFromGrid xGrid, yGrid, centers, outerRegions.count
        ZoomToGridWindow doc, gridMinX, gridMinY, zoomMaxX, zoomMaxY, 0.1
    End If

    ' If the dominant dimension still exceeds its cell dimension after the first upscale,
    ' apply an additional upscale so every cell can contain the region without clipping.
    ' Only 85% of cellHeight is available for the shape body; the remaining 15% is reserved for header text.
    Const CELL_BODY_RATIO As Double = 0.85
    Dim effectiveCellHeight As Double
    effectiveCellHeight = cellHeight * CELL_BODY_RATIO
    Dim needsSecondScale As Boolean
    If orientMode = 1 Then
        ' Vertical: check region width vs cell width
        needsSecondScale = (maxWidth > 0 And cellWidth > 0 And cellWidth < maxWidth * widthPaddingFactor)
    ElseIf orientMode = 2 Then
        ' Diagonal: both dimensions already handled in scaleFactor; no second scale needed
        needsSecondScale = False
    Else
        ' Horizontal: check region height vs effective cell height
        needsSecondScale = (maxHeight > 0 And effectiveCellHeight > 0 And effectiveCellHeight < maxHeight)
    End If
    If needsSecondScale Then
        Dim heightAdjFactor As Double
        If orientMode = 1 Then
            heightAdjFactor = (maxWidth * widthPaddingFactor) / cellWidth
        Else
            heightAdjFactor = (maxHeight * heightPaddingFactor) / effectiveCellHeight
        End If
        Dim hOrigin(0 To 2) As Double
        Dim hGridMin As Variant, hGridMax As Variant
        GetSelectionSetBounds gridSS, hGridMin, hGridMax
        hOrigin(0) = hGridMin(0)
        hOrigin(1) = hGridMin(1)
        hOrigin(2) = 0
        ScaleEntitiesInSelection gridSS, hOrigin, heightAdjFactor
        ScaleGridData xGrid, yGrid, hOrigin, heightAdjFactor
        gridMinX = hOrigin(0) + (gridMinX - hOrigin(0)) * heightAdjFactor
        gridMinY = hOrigin(1) + (gridMinY - hOrigin(1)) * heightAdjFactor
        gridMaxX = hOrigin(0) + (gridMaxX - hOrigin(0)) * heightAdjFactor
        gridMaxY = hOrigin(1) + (gridMaxY - hOrigin(1)) * heightAdjFactor
        zoomMaxX = hOrigin(0) + (zoomMaxX - hOrigin(0)) * heightAdjFactor
        zoomMaxY = hOrigin(1) + (zoomMaxY - hOrigin(1)) * heightAdjFactor
        cellWidth = AverageStep(xGrid)
        cellHeight = AverageStep(yGrid)
        RebuildCentersFromGrid xGrid, yGrid, centers, outerRegions.count
        ZoomToGridWindow doc, gridMinX, gridMinY, zoomMaxX, zoomMaxY, 0.1
    End If
    
    ' Visualize grid centers AFTER scaling (red points)
    VisualizeGridCenters doc, centers, xGrid, acRed, "Após a Escala"
    DistributeToGrid regionEntities, centers, xGrid, yGrid, cellHeight

    If fillHeaders Then
        CreateHeaderLabels doc, regionLabels, centers, cellHeight, cellWidth, gridSS
    End If
    
    ExportShapesToDxf regionEntities, regionLabels
    
Cleanup:
    On Error Resume Next
    If Not shapesLayer Is Nothing Then
        shapesLayer.LayerOn = False
    Else
        Dim cleanupLayer As AcadLayer
        Set cleanupLayer = doc.layers.item("Shapes")
        If Err.Number = 0 And Not cleanupLayer Is Nothing Then cleanupLayer.LayerOn = False
        Err.Clear
    End If
    If Not gridSS Is Nothing Then gridSS.Delete
    shapeSS.Delete
    doc.EndUndoMark
    If Not formPerfisul01 Is Nothing Then
        ' Move form to 75% of screen width
        ' formPerfisul01.StartUpPosition = 0 ' Manual
        ' 0.75 factor for screen width percentage
        ' 0.75 factor for rough Pixel to Point conversion (Typical 96 DPI: 1 px = 0.75 pt)
        Dim screenWidthPts As Double
        screenWidthPts = GetSystemMetrics(SM_CXSCREEN) * 0.75
        
        formPerfisul01.StartUpPosition = 0
        formPerfisul01.Left = screenWidthPts * 0.75
        formPerfisul01.top = 100
        formPerfisul01.Show
    End If
    Exit Sub
    
ErrHandler:
    MsgBox "Erro: " & Err.Description, vbCritical, "Distribuir Formas"
    Resume Cleanup
End Sub

'-----------------------------
' Shape detection and grouping
'-----------------------------

Private Function IsExcludedContourLayer(layerName As String) As Boolean
    Dim lname As String
    lname = UCase$(layerName)
    IsExcludedContourLayer = (InStr(1, lname, UCase$("Gravação"), vbTextCompare) > 0) Or _
                             (InStr(1, lname, UCase$("Dobra"), vbTextCompare) > 0) Or _
                             (InStr(1, lname, UCase$("Texto"), vbTextCompare) > 0)
End Function

Private Function DetectOuterRegionsFromSelection(doc As AcadDocument, ss As AcadSelectionSet, ByRef allRegions As collection) As collection
    ' Build object array excluding entities from layers containing "Gravação", "Dobra" or "Texto"
    Dim objs() As Object
    Dim i As Long
    Dim objCount As Long: objCount = 0
    ReDim objs(ss.count - 1)
    For i = 0 To ss.count - 1
        Dim candidate As AcadEntity
        Set candidate = ss.item(i)
        If Not IsExcludedContourLayer(candidate.layer) Then
            Set objs(objCount) = candidate
            objCount = objCount + 1
        End If
    Next i
    If objCount = 0 Then Exit Function
    ReDim Preserve objs(0 To objCount - 1)
    
    Dim created As Variant
    On Error Resume Next
    created = doc.modelSpace.AddRegion(objs)
    If Err.Number <> 0 Or IsEmpty(created) Then
        Err.Clear
        Exit Function
    End If
    On Error GoTo 0
    
    Dim regArr() As AcadRegion
    Dim idx As Long
    ReDim regArr(LBound(created) To UBound(created))
    idx = LBound(created)
    Dim r As Variant
    For Each r In created
        Set regArr(idx) = r
        idx = idx + 1
    Next r

    Dim shapesLayer As AcadLayer
    Set shapesLayer = EnsureShapesLayer(doc)
    For i = LBound(regArr) To UBound(regArr)
        On Error Resume Next
        regArr(i).layer = "Shapes"
        regArr(i).Color = acByLayer
        Err.Clear
        On Error GoTo 0
    Next i

    Set allRegions = New collection
    For i = LBound(regArr) To UBound(regArr)
        allRegions.Add regArr(i)
    Next i

    Set DetectOuterRegionsFromSelection = FilterOuterRegions(regArr)
End Function

Private Function FilterOuterRegions(regArr() As AcadRegion) As collection
    Dim count As Long
    count = UBound(regArr) - LBound(regArr) + 1
    If count = 0 Then Exit Function
    
    Dim i As Long, j As Long
    Dim swapped As Boolean
    Dim tmp As AcadRegion
    ' Sort by area desc
    Do
        swapped = False
        For i = LBound(regArr) To UBound(regArr) - 1
            If regArr(i).area < regArr(i + 1).area Then
                Set tmp = regArr(i)
                Set regArr(i) = regArr(i + 1)
                Set regArr(i + 1) = tmp
                swapped = True
            End If
        Next i
    Loop While swapped
    
    Dim keepFlags() As Boolean
    ReDim keepFlags(LBound(regArr) To UBound(regArr))
    For i = LBound(regArr) To UBound(regArr)
        keepFlags(i) = True
    Next i
    
    Dim testReg As AcadRegion, containerReg As AcadRegion
    Dim copyA As AcadRegion, copyB As AcadRegion
    For i = LBound(regArr) To UBound(regArr)
        If keepFlags(i) Then
            Set testReg = regArr(i)
            For j = LBound(regArr) To UBound(regArr)
                If i <> j And keepFlags(j) Then
                    Set containerReg = regArr(j)
                    If containerReg.area >= testReg.area Then
                        On Error Resume Next
                        Set copyA = testReg.Copy
                        Set copyB = containerReg.Copy
                        copyA.Boolean acIntersection, copyB
                        If Err.Number = 0 Then
                            If Abs(copyA.area - testReg.area) < 0.0001 Then
                                keepFlags(i) = False
                                copyA.Delete
                                copyB.Delete
                                Exit For
                            End If
                        End If
                        If Not copyA Is Nothing Then copyA.Delete
                        If Not copyB Is Nothing Then copyB.Delete
                        Err.Clear
                        On Error GoTo 0
                    End If
                End If
            Next j
        End If
    Next i
    
    ' Inner regions (holes) are intentionally kept as separate entities on the Shapes layer.
    ' CollectEntitiesForRegion will pick them up via the allRegions collection and move them
    ' together with their containing outer shape. sheetMetalWeight uses an even-odd nesting
    ' depth rule: depth-0 regions add area (outer material), depth-1 regions subtract area
    ' (holes). Merging holes into the outer region via Boolean acSubtraction was causing two
    ' problems: the resulting complex region's Color property no longer returned acByLayer,
    ' making it undetectable; and it destroyed the hole geometry as a separate entity,
    ' breaking the nesting-depth algorithm in sheetMetalWeight.
    ' Orphaned inner regions (no containing outer found) are deleted to avoid clutter.
    Dim holeArea As Double
    Dim bestContainerArea As Double
    Dim bestContainerIdx As Long
    Dim contArea As Double
    For i = LBound(regArr) To UBound(regArr)
        If Not keepFlags(i) Then
            Set testReg = regArr(i)
            holeArea = testReg.area
            bestContainerIdx = -1
            bestContainerArea = 1E+30
            For j = LBound(regArr) To UBound(regArr)
                If keepFlags(j) Then
                    Set containerReg = regArr(j)
                    contArea = containerReg.area
                    If contArea >= holeArea And contArea < bestContainerArea Then
                        On Error Resume Next
                        Set copyA = testReg.Copy
                        Set copyB = containerReg.Copy
                        copyA.Boolean acIntersection, copyB
                        If Err.Number = 0 Then
                            If Abs(copyA.area - holeArea) < 0.0001 Then
                                bestContainerIdx = j
                                bestContainerArea = contArea
                            End If
                        End If
                        If Not copyA Is Nothing Then copyA.Delete
                        If Not copyB Is Nothing Then copyB.Delete
                        Err.Clear
                        On Error GoTo 0
                    End If
                End If
            Next j
            ' Delete only orphaned inner regions (no container found); contained holes stay.
            If bestContainerIdx < 0 Then
                On Error Resume Next
                testReg.Delete
                Err.Clear
                On Error GoTo 0
            End If
        End If
    Next i

    Dim result As New collection
    For i = LBound(regArr) To UBound(regArr)
        If keepFlags(i) Then result.Add regArr(i)
    Next i
    Set FilterOuterRegions = result
End Function

Private Function CollectEntitiesForRegion(reg As AcadRegion, ss As AcadSelectionSet, allRegions As collection) As collection
    Dim col As New collection
    Dim regMin As Variant, regMax As Variant
    reg.GetBoundingBox regMin, regMax
    
    Dim regCx As Double, regCy As Double
    regCx = (regMin(0) + regMax(0)) / 2
    regCy = (regMin(1) + regMax(1)) / 2
    
    Dim ent As AcadEntity
    For Each ent In ss
        Dim eMin As Variant, eMax As Variant
        Dim cx As Double, cy As Double
        Dim gotCenter As Boolean: gotCenter = False
        On Error Resume Next
        ent.GetBoundingBox eMin, eMax
        If Err.Number = 0 Then
            cx = (eMin(0) + eMax(0)) / 2
            cy = (eMin(1) + eMax(1)) / 2
            gotCenter = True
        Else
            Err.Clear
            ' Fallback for MText/Text: use InsertionPoint when GetBoundingBox fails
            If TypeOf ent Is AcadMText Or TypeOf ent Is AcadText Then
                Dim insPt As Variant
                insPt = ent.InsertionPoint
                If Err.Number = 0 Then
                    cx = insPt(0)
                    cy = insPt(1)
                    gotCenter = True
                End If
            End If
        End If
        Err.Clear
        If gotCenter Then
            If cx >= regMin(0) - 0.01 And cx <= regMax(0) + 0.01 And _
               cy >= regMin(1) - 0.01 And cy <= regMax(1) + 0.01 Then
                col.Add ent
            End If
        End If
        On Error GoTo 0
    Next ent

    If Not allRegions Is Nothing Then
        Dim regEnt As AcadRegion
        For Each regEnt In allRegions
            If regEnt Is reg Then GoTo NextReg
            Dim rMin As Variant, rMax As Variant
            On Error Resume Next
            regEnt.GetBoundingBox rMin, rMax
            If Err.Number = 0 Then
                Dim rcx As Double, rcy As Double
                rcx = (rMin(0) + rMax(0)) / 2
                rcy = (rMin(1) + rMax(1)) / 2
                If rcx >= regMin(0) - 0.01 And rcx <= regMax(0) + 0.01 And _
                   rcy >= regMin(1) - 0.01 And rcy <= regMax(1) + 0.01 Then
                    col.Add regEnt
                End If
            End If
            Err.Clear
            On Error GoTo 0
NextReg:
        Next regEnt
    End If
    col.Add reg
    Set CollectEntitiesForRegion = col
End Function

Private Function GetEntitySetCenter(entObj As AcadEntity) As Double()
    Dim minPt As Variant, maxPt As Variant
    entObj.GetBoundingBox minPt, maxPt
    Dim c(0 To 2) As Double
    c(0) = (minPt(0) + maxPt(0)) / 2
    c(1) = (minPt(1) + maxPt(1)) / 2
    c(2) = 0
    GetEntitySetCenter = c
End Function

'-----------------------------
' Orientation helpers
'-----------------------------

Private Function FindBestRotationAngleForEntities(ents As collection, centerPt() As Double, ByRef dimensionOut As Double, Optional minimizeWidth As Boolean = False) As Double
    Const STEP_DEG As Double = 1
    Const PI As Double = 3.14159265358979
    
    Dim points() As Point2D
    Dim numPoints As Long
    numPoints = CollectSamplingPointsFromCollection(ents, centerPt, points)
    
    Dim bestAngle As Double: bestAngle = 0
    Dim bestDim As Double: bestDim = 1E+30
    Dim bestAspect As Double: bestAspect = 0
    
    Dim deg As Double, angle As Double
    Dim width As Double, height As Double, aspect As Double
    For deg = 0 To 180 Step STEP_DEG
        angle = deg * PI / 180
        GetRotatedBoundsFromPoints points, numPoints, angle, width, height
        Dim targetDim As Double
        If minimizeWidth Then
            targetDim = width
            If width > 0 Then aspect = height / width Else aspect = 0
        Else
            targetDim = height
            If height > 0 Then aspect = width / height Else aspect = 0
        End If
        If targetDim < bestDim - 0.001 Or (Abs(targetDim - bestDim) < 0.001 And aspect > bestAspect) Then
            bestDim = targetDim
            bestAspect = aspect
            bestAngle = angle
        End If
    Next deg
    dimensionOut = bestDim
    FindBestRotationAngleForEntities = bestAngle
End Function

' Find the rotation angle (0–180°) that makes the shape's bounding-box diagonal angle
' closest to the target cell diagonal angle (in radians, measured from horizontal).
Private Function FindDiagonalRotationAngleForEntities(ents As collection, centerPt() As Double, cellDiagAngle As Double) As Double
    Const STEP_DEG As Double = 1
    Const PI_FD As Double = 3.14159265358979

    Dim points() As Point2D
    Dim numPoints As Long
    numPoints = CollectSamplingPointsFromCollection(ents, centerPt, points)

    Dim bestAngle As Double: bestAngle = 0
    Dim bestDiff As Double: bestDiff = 1E+30

    Dim deg As Double, angle As Double
    Dim width As Double, height As Double
    Dim shapeDiagAngle As Double, diff As Double
    For deg = 0 To 180 Step STEP_DEG
        angle = deg * PI_FD / 180
        GetRotatedBoundsFromPoints points, numPoints, angle, width, height
        If width > 0 Then
            shapeDiagAngle = Atn(height / width)
        Else
            shapeDiagAngle = PI_FD / 2
        End If
        diff = Abs(shapeDiagAngle - cellDiagAngle)
        If diff > PI_FD / 2 Then diff = PI_FD - diff  ' wrap to [0, p/2]
        If diff < bestDiff Then
            bestDiff = diff
            bestAngle = angle
        End If
    Next deg
    FindDiagonalRotationAngleForEntities = bestAngle
End Function

Private Function CollectSamplingPointsFromCollection(ents As collection, centerPt() As Double, ByRef pointsOut() As Point2D) As Long
    Dim ent As AcadEntity
    Dim count As Long: count = 0
    ReDim pointsOut(0 To 1000) As Point2D
    For Each ent In ents
        If IsExcludedFromAngleCalculation(ent) Then GoTo NextEnt
        Dim name As String
        name = UCase$(ent.ObjectName)
        If InStr(1, name, "POLYLINE", vbTextCompare) > 0 Then
            CollectPolylinePoints ent, centerPt, pointsOut, count
        ElseIf InStr(1, name, "REGION", vbTextCompare) > 0 Then
            CollectRegionPoints ent, centerPt, pointsOut, count
        ElseIf name = "ACDBLINE" Or name = "ACADLINE" Then
            CollectLinePoints ent, centerPt, pointsOut, count
        ElseIf name = "ACDBARC" Or name = "ACADARC" Then
            CollectArcPoints ent, centerPt, pointsOut, count
        Else
            CollectBoundingBoxPoints ent, centerPt, pointsOut, count
        End If
NextEnt:
    Next ent
    CollectSamplingPointsFromCollection = count
End Function

Private Function IsExcludedFromAngleCalculation(ent As AcadEntity) As Boolean
    Dim nm As String
    nm = UCase$(ent.ObjectName)
    If InStr(1, nm, "REGION", vbTextCompare) > 0 Then
        IsExcludedFromAngleCalculation = True
        Exit Function
    End If
    Dim layerName As String
    layerName = UCase$(Trim$(ent.layer))
    If layerName = "SHAPES" Then
        IsExcludedFromAngleCalculation = True
        Exit Function
    End If
    IsExcludedFromAngleCalculation = False
End Function

Private Sub RotateEntities(ents As collection, centerPt() As Double, angle As Double)
    Dim ent As AcadEntity
    For Each ent In ents
        On Error Resume Next
        ent.Rotate centerPt, angle
        Err.Clear
        On Error GoTo 0
    Next ent
End Sub

Private Sub ScaleEntities(ents As collection, centerPt() As Double, scaleFactor As Double)
    If Abs(scaleFactor - 1) < 0.0001 Then Exit Sub
    Dim ent As AcadEntity
    For Each ent In ents
        On Error Resume Next
        ent.ScaleEntity centerPt, scaleFactor
        Err.Clear
        On Error GoTo 0
    Next ent
End Sub

Private Sub ScaleEntitiesInSelection(ss As AcadSelectionSet, origin() As Double, scaleFactor As Double)
    If ss Is Nothing Then Exit Sub
    If Abs(scaleFactor - 1) < 0.0001 Then Exit Sub
    Dim ent As AcadEntity
    For Each ent In ss
        On Error Resume Next
        ent.ScaleEntity origin, scaleFactor
        Err.Clear
        On Error GoTo 0
    Next ent
End Sub

Private Sub GetEntitiesBounds(ents As collection, ByRef minPt As Variant, ByRef maxPt As Variant)
    ' Calculate the bounding box encompassing all entities in the collection
    Dim minX As Double, minY As Double, maxX As Double, maxY As Double
    Dim first As Boolean: first = True
    
    Dim ent As AcadEntity
    Dim eMin As Variant, eMax As Variant
    
    ' Iterate through each entity to find overall min/max coordinates
    For Each ent In ents
        On Error Resume Next
        ' Get individual entity's bounding box
        ent.GetBoundingBox eMin, eMax
        If Err.Number = 0 Then
            ' On first entity, initialize bounds
            If first Then
                minX = eMin(0): minY = eMin(1): maxX = eMax(0): maxY = eMax(1)
                first = False
            Else
                ' On subsequent entities, expand bounds if needed
                If eMin(0) < minX Then minX = eMin(0)
                If eMin(1) < minY Then minY = eMin(1)
                If eMax(0) > maxX Then maxX = eMax(0)
                If eMax(1) > maxY Then maxY = eMax(1)
            End If
        End If
        Err.Clear
        On Error GoTo 0
    Next ent
    
    ' Return bounding box as [minX, minY, Z] and [maxX, maxY, Z]
    minPt = Array(minX, minY, 0)
    maxPt = Array(maxX, maxY, 0)
End Sub

Private Sub GetSelectionSetBounds(ss As AcadSelectionSet, ByRef minPt As Variant, ByRef maxPt As Variant)
    ' Bounding box for a selection set
    Dim minX As Double, minY As Double, maxX As Double, maxY As Double
    Dim first As Boolean: first = True
    Dim ent As AcadEntity
    Dim eMin As Variant, eMax As Variant
    For Each ent In ss
        On Error Resume Next
        ent.GetBoundingBox eMin, eMax
        If Err.Number = 0 Then
            If first Then
                minX = eMin(0): minY = eMin(1): maxX = eMax(0): maxY = eMax(1)
                first = False
            Else
                If eMin(0) < minX Then minX = eMin(0)
                If eMin(1) < minY Then minY = eMin(1)
                If eMax(0) > maxX Then maxX = eMax(0)
                If eMax(1) > maxY Then maxY = eMax(1)
            End If
        End If
        Err.Clear
        On Error GoTo 0
    Next ent
    minPt = Array(minX, minY, 0)
    maxPt = Array(maxX, maxY, 0)
End Sub

Private Sub MoveEntities(ents As collection, fromPt() As Double, toPt() As Double)
    ' Move all entities from one point to another
    Dim ent As AcadEntity
    For Each ent In ents
        On Error Resume Next
        ' Move the entity: calculates translation vector and applies to all geometry
        ent.Move fromPt, toPt
        Err.Clear
        On Error GoTo 0
    Next ent
End Sub

Private Sub ScaleGridData(ByRef xGrid() As Double, ByRef yGrid() As Double, origin() As Double, scaleFactor As Double)
    Dim i As Long
    For i = 0 To UBound(xGrid)
        xGrid(i) = origin(0) + (xGrid(i) - origin(0)) * scaleFactor
    Next i
    For i = 0 To UBound(yGrid)
        yGrid(i) = origin(1) + (yGrid(i) - origin(1)) * scaleFactor
    Next i
End Sub

'-----------------------------
' Grid detection
'-----------------------------

Private Function DetectGridFromUserSelection(centers As collection, ByRef cellWidth As Double, ByRef cellHeight As Double, _
    ByRef xGrid() As Double, ByRef yGrid() As Double, ByRef cols As Long, ByRef rows As Long, _
    ByRef gridSS As AcadSelectionSet, ByRef gridMinXOut As Double, ByRef gridMinYOut As Double, _
    ByRef gridMaxXOut As Double, ByRef gridMaxYOut As Double, ByRef zoomMaxXOut As Double, _
    ByRef zoomMaxYOut As Double, ByRef hasTopRightCornerOut As Boolean, Optional regionCount As Long = -1) As Boolean
    
    ' Radius offset multipliers for grid corner calculation
    Const HORIZONTAL_RADIUS_MULTIPLIER As Double = 1.2
    Const VERTICAL_RADIUS_MULTIPLIER As Double = 1.2

    Dim hasTopRightCorner As Boolean
    Dim topRightX As Double, topRightY As Double
    
    Dim sset As AcadSelectionSet
    Set sset = PrepareSelectionSet(ThisDrawing, "DSG_GRID")
    MsgBox "Selecione a área cobrindo as linhas da grade.", vbInformation, "Distribuir Formas"
    sset.SelectOnScreen
    If sset.count = 0 Then Exit Function
    
    Dim xArr() As Double, yArr() As Double
    ReDim xArr(0 To 200)
    ReDim yArr(0 To 200)
    Dim xCount As Long, yCount As Long
    xCount = 0: yCount = 0
    
    ' Find circles to determine grid extent
    Dim circles As collection
    Set circles = New collection
    Dim circleRadii As collection
    Set circleRadii = New collection
    
    Dim ent As AcadEntity
    For Each ent In sset
        If ent.ObjectName = "AcDbLine" Then
            Dim ln As AcadLine
            Set ln = ent
            Dim sx As Double, sy As Double, ex As Double, ey As Double
            sx = ln.startPoint(0): sy = ln.startPoint(1)
            ex = ln.endPoint(0): ey = ln.endPoint(1)
            If Abs(sx - ex) < 0.1 Then AddUniqueVal xArr, xCount, (sx + ex) / 2
            If Abs(sy - ey) < 0.1 Then AddUniqueVal yArr, yCount, (sy + ey) / 2
        ElseIf ent.ObjectName = "AcDbCircle" Then
            Dim circ As AcadCircle
            Set circ = ent
            Dim circCenter As Variant
            circCenter = circ.center
            circles.Add circCenter
            circleRadii.Add circ.radius
        End If
    Next ent
    
    If xCount < 2 Or yCount < 2 Then
        MsgBox "Grade inválida. Verticais: " & xCount & " horizontais: " & yCount, vbExclamation, "Distribuir Formas"
        sset.Delete
        Exit Function
    End If
    
    SortDoubles xArr, xCount
    SortDoubles yArr, yCount
    xCount = MergeCloseSorted(xArr, xCount)
    yCount = MergeCloseSorted(yArr, yCount)

    ' Selection bounds are the fallback zoom bounds.
    Dim selectionMin As Variant, selectionMax As Variant
    GetSelectionSetBounds sset, selectionMin, selectionMax
    zoomMaxXOut = selectionMax(0)
    zoomMaxYOut = selectionMax(1)
    
    ' If circles were found, use them to determine grid extent
    If circles.count > 0 Then
        ' Sort circles by Y (descending, top to bottom) then by X (ascending, left to right)
        Dim i As Long, j As Long
        Dim circleWidth As Double
        Dim sortedCircles As collection
        Dim sortedRadii As collection
        Set sortedCircles = New collection
        Set sortedRadii = New collection
        
        ' Simple bubble sort by Y descending, then X ascending
        Dim circArray() As Variant
        ReDim circArray(1 To circles.count)
        Dim radArray() As Double
        ReDim radArray(1 To circles.count)
        
        For i = 1 To circles.count
            circArray(i) = circles(i)
            radArray(i) = circleRadii(i)
        Next i
        
        Dim swapped As Boolean
        For i = 1 To circles.count - 1
            swapped = False
            For j = 1 To circles.count - i
                Dim y1 As Double, y2 As Double, x1 As Double, x2 As Double
                y1 = CDbl(circArray(j)(1))
                y2 = CDbl(circArray(j + 1)(1))
                x1 = CDbl(circArray(j)(0))
                x2 = CDbl(circArray(j + 1)(0))
                
                If y1 < y2 Or (Abs(y1 - y2) < 0.1 And x1 > x2) Then
                    Dim tmpArr As Variant
                    Dim tmpRad As Double
                    tmpArr = circArray(j)
                    tmpRad = radArray(j)
                    circArray(j) = circArray(j + 1)
                    radArray(j) = radArray(j + 1)
                    circArray(j + 1) = tmpArr
                    radArray(j + 1) = tmpRad
                    swapped = True
                End If
            Next j
            If Not swapped Then Exit For
        Next i
        
        ' Find the rightmost circle in the first row
        Dim firstRowY As Double
        firstRowY = CDbl(circArray(1)(1))
        Dim lastCircleInFirstRow As Variant
        Dim lastRadiusInFirstRow As Double
        Dim circleCount As Long: circleCount = 0
        
        For i = 1 To circles.count
            If Abs(CDbl(circArray(i)(1)) - firstRowY) < 0.1 Then
                lastCircleInFirstRow = circArray(i)
                lastRadiusInFirstRow = radArray(i)
                circleCount = i
            Else
                Exit For
            End If
        Next i

        ' Horizontal cell width derived from mean X offset between first-row circles
        If circleCount >= 2 Then
            Dim widthSum As Double
            For i = 1 To circleCount - 1
                widthSum = widthSum + (CDbl(circArray(i + 1)(0)) - CDbl(circArray(i)(0)))
            Next i
            circleWidth = widthSum / (circleCount - 1)
        End If
        
        ' Calculate grid extent from the last circle in first row
        topRightX = CDbl(lastCircleInFirstRow(0)) + lastRadiusInFirstRow * HORIZONTAL_RADIUS_MULTIPLIER
        topRightY = CDbl(lastCircleInFirstRow(1)) + lastRadiusInFirstRow * VERTICAL_RADIUS_MULTIPLIER
        hasTopRightCorner = True

        ' Derive vertical cell height from first circle in first and second rows
        Dim circleHeightStep As Double
        If circles.count >= circleCount + 1 And circleCount > 0 Then
            circleHeightStep = Abs(CDbl(circArray(1)(1)) - CDbl(circArray(circleCount + 1)(1)))
        End If
        
        ' Adjust grid arrays to match circle positions
        ' xArr should represent the column lines
        ' yArr should represent the row lines
        ' Use the circles themselves to refine the grid
        cols = circleCount - 1
        rows = circles.count \ circleCount - 1
    End If
    
    ReDim xGrid(0 To xCount - 1)
    ReDim yGrid(0 To yCount - 1)
    Dim k As Long
    For k = 0 To xCount - 1: xGrid(k) = xArr(k): Next k
    For k = 0 To yCount - 1: yGrid(k) = yArr(k): Next k

    ' Override X grid using circle-based width so column centers follow reference circles
    If circleWidth > 0 And circleCount > 0 Then
        xCount = circleCount + 1
        ReDim xGrid(0 To xCount - 1)
        Dim leftEdge As Double
        leftEdge = CDbl(circArray(1)(0)) + HORIZONTAL_RADIUS_MULTIPLIER * radArray(1) - circleWidth
        For k = 0 To xCount - 1
            xGrid(k) = leftEdge + circleWidth * k
        Next k
    End If
    
    If cols = 0 Then cols = xCount - 1
    If rows = 0 Then rows = yCount - 1
    cellWidth = AverageStep(xGrid)
    cellHeight = AverageStep(yGrid)

    ' If we obtained a circle-based vertical step, prefer it for consistent row spacing
    If circleHeightStep > 0.000001 Then cellHeight = circleHeightStep

    ' Anchor top-right corner from the last circle in first row (circle-based extents)
    If hasTopRightCorner Then
        If yCount > 0 Then yGrid(yCount - 1) = topRightY
        If xCount > 0 Then xGrid(xCount - 1) = topRightX
    End If

    ' Normalize all Y grid lines to be equally spaced so every row step equals the averaged cellHeight
    If yCount >= 2 Then
        Dim topY As Double
        topY = yGrid(yCount - 1)
        For i = 0 To yCount - 1
            yGrid(yCount - 1 - i) = topY - cellHeight * i
        Next i
    End If
    
    BuildCenters xGrid, yGrid, centers, regionCount
    gridMinXOut = xGrid(0)
    gridMinYOut = yGrid(0)
    gridMaxXOut = xGrid(UBound(xGrid))
    gridMaxYOut = yGrid(UBound(yGrid))
    hasTopRightCornerOut = hasTopRightCorner
    If hasTopRightCorner Then
        gridMaxXOut = topRightX
        gridMaxYOut = topRightY
        zoomMaxXOut = topRightX
        zoomMaxYOut = topRightY
    End If
    Set gridSS = sset
    DetectGridFromUserSelection = True
End Function

Private Sub BuildCenters(xGrid() As Double, yGrid() As Double, centers As collection, Optional maxCenters As Long = -1)
    ' Generate center points for all grid cells by iterating rows and columns.
    ' If maxCenters >= 0, stop once that many centers have been added.
    Dim r As Long, c As Long
    
    ' Iterate rows from top to bottom (reverse order: highest Y first)
    For r = UBound(yGrid) - 1 To 0 Step -1
        ' Iterate columns from left to right
        For c = 0 To UBound(xGrid) - 1
            ' Stop if we have reached the requested number of centers
            If maxCenters >= 0 And centers.count >= maxCenters Then Exit Sub
            
            ' Create center point for this cell
            Dim pt(0 To 2) As Double
            
            ' Horizontal center: midpoint between adjacent X grid lines
            pt(0) = (xGrid(c) + xGrid(c + 1)) / 2
            
            ' Vertical center: midpoint between adjacent Y grid lines
            pt(1) = (yGrid(r) + yGrid(r + 1)) / 2
            
            ' Z coordinate (depth)
            pt(2) = 0
            
            ' Add this cell center to collection
            centers.Add pt
        Next c
    Next r
End Sub

Private Sub RebuildCentersFromGrid(xGrid() As Double, yGrid() As Double, centers As collection, Optional maxCenters As Long = -1)
    ' Clear existing centers and rebuild from current grid state
    ' This is used after scaling the grid to recalculate all cell centers
    Do While centers.count > 0
        centers.Remove 1
    Loop
    BuildCenters xGrid, yGrid, centers, maxCenters
End Sub

Private Sub ZoomToGridWindow(doc As AcadDocument, minX As Double, minY As Double, maxX As Double, maxY As Double, Optional paddingRatio As Double = 0.1)
    On Error Resume Next
    minX = 0
    minY = 0
    If maxX <= minX Or maxY <= minY Then Exit Sub

    Dim gridW As Double, gridH As Double
    gridW = maxX - minX
    gridH = maxY - minY
    If gridW <= 0.000001 Or gridH <= 0.000001 Then Exit Sub

    Dim padX As Double, padY As Double
    padX = gridW * paddingRatio
    padY = gridH * paddingRatio

    Dim ll(0 To 2) As Double
    Dim ur(0 To 2) As Double
    ll(0) = minX - padX
    ll(1) = minY - padY
    ll(2) = 0
    ur(0) = maxX + padX
    ur(1) = maxY + 2 * padY
    ur(2) = 0

    doc.Application.ZoomWindow ll, ur
    Err.Clear
    On Error GoTo 0
End Sub

Private Function AverageStep(arr() As Double) As Double
    Dim i As Long, total As Double
    For i = 0 To UBound(arr) - 1
        total = total + (arr(i + 1) - arr(i))
    Next i
    If UBound(arr) > 0 Then
        AverageStep = total / (UBound(arr))
    Else
        AverageStep = 0
    End If
End Function

Private Sub AddUniqueVal(ByRef arr() As Double, ByRef count As Long, val As Double)
    Dim i As Long
    For i = 0 To count - 1
        If Abs(arr(i) - val) < 0.1 Then Exit Sub
    Next i
    If count > UBound(arr) Then ReDim Preserve arr(0 To UBound(arr) + 50)
    arr(count) = val
    count = count + 1
End Sub

Private Sub SortDoubles(ByRef arr() As Double, count As Long)
    Dim i As Long, j As Long, tmp As Double
    For i = 0 To count - 2
        For j = i + 1 To count - 1
            If arr(i) > arr(j) Then
                tmp = arr(i): arr(i) = arr(j): arr(j) = tmp
            End If
        Next j
    Next i
End Sub

Private Function MergeCloseSorted(ByRef arr() As Double, count As Long) As Long
    If count <= 1 Then
        MergeCloseSorted = count
        Exit Function
    End If
    Dim minStep As Double: minStep = 0
    Dim i As Long
    For i = 0 To count - 2
        Dim d As Double
        d = Abs(arr(i + 1) - arr(i))
        If d > 0.000001 Then
            If minStep = 0 Or d < minStep Then minStep = d
        End If
    Next i
    If minStep = 0 Then
        MergeCloseSorted = 1
        arr(0) = arr(0)
        Exit Function
    End If
    Dim tol As Double
    tol = minStep * 1.05
    Dim writeIdx As Long: writeIdx = 0
    For i = 0 To count - 1
        If writeIdx = 0 Then
            arr(writeIdx) = arr(i)
            writeIdx = writeIdx + 1
        Else
            If Abs(arr(i) - arr(writeIdx - 1)) > tol Then
                arr(writeIdx) = arr(i)
                writeIdx = writeIdx + 1
            End If
        End If
    Next i
    MergeCloseSorted = writeIdx
End Function

'-----------------------------
' Distribution
'-----------------------------

Private Sub DistributeToGrid(regionEntities As collection, centers As collection, xGrid() As Double, yGrid() As Double, cellHeight As Double)
    ' Vertical positioning fine-tuning: adjust this offset to move all extra rows up/down
    ' Positive value = move down, Negative value = move up
    Const VERTICAL_OFFSET As Double = 0
    
    ' Calculate if additional rows are needed beyond the initial grid
    Dim totalCells As Long
    totalCells = centers.count
    Dim need As Long
    need = regionEntities.count - totalCells
    Dim extraRows As Long
    
    ' If there are more shapes than grid cells, create additional rows below the grid
    If need > 0 Then
        Dim cols As Long
        cols = UBound(xGrid)
        extraRows = (need + cols - 1) \ cols
        AppendExtraRows centers, xGrid, yGrid(0), cellHeight, extraRows, VERTICAL_OFFSET
    End If
    
    ' Move each shape to its assigned grid cell center
    Dim i As Long
    For i = 1 To regionEntities.count
        ' Check if we have a corresponding center point for this shape
        If i > centers.count Then Exit For
        
        ' Get target center point from grid
        Dim tgt() As Double
        tgt = centers(i)
        
        ' Calculate current geometric center of the shape from its bounding box
        Dim minPt As Variant, maxPt As Variant
        GetEntitiesBounds regionEntities(i), minPt, maxPt
        
        ' Extract current center X and Y coordinates
        Dim curr(0 To 2) As Double
        curr(0) = (minPt(0) + maxPt(0)) / 2
        curr(1) = (minPt(1) + maxPt(1)) / 2
        curr(2) = 0
        
        ' Move shape from current center to target grid cell center
        MoveEntities regionEntities(i), curr, tgt
    Next i
End Sub

Private Sub AppendExtraRows(centers As collection, xGrid() As Double, baseY As Double, cellHeight As Double, extraRows As Long, Optional verticalOffset As Double = 0)
    ' Generate center points for additional grid rows needed beyond the initial grid
    Dim r As Long, c As Long
    
    ' For each extra row to be created
    For r = 1 To extraRows
        ' For each column in the grid
        For c = 0 To UBound(xGrid) - 1
            ' Create a new center point for this row/column intersection
            Dim pt(0 To 2) As Double
            
            ' Horizontal: center of the cell width
            pt(0) = (xGrid(c) + xGrid(c + 1)) / 2
            
            ' Vertical: position below the base grid by (r * cellHeight) with offset to cell center
            ' Fine-tuned formula: baseY - (cellHeight * r) + (cellHeight / 2) + verticalOffset
            ' verticalOffset allows adjustment of all extra rows relative to base grid
            pt(1) = baseY - (cellHeight * r) + (cellHeight / 2) + verticalOffset
            
            ' Z coordinate (depth)
            pt(2) = 0
            
            ' Add this center point to the collection
            centers.Add pt
        Next c
    Next r
End Sub

Private Sub CreateHeaderLabels(doc As AcadDocument, labels() As String, centers As collection, _
    cellHeight As Double, cellWidth As Double, gridSS As AcadSelectionSet)
    
    If gridSS Is Nothing Then Exit Sub
    
    Dim i As Long
    Dim centerPt As Variant
    Dim ent As AcadEntity
    Dim eMin As Variant, eMax As Variant
    Dim cellMinX As Double, cellMaxX As Double
    Dim cellMinY As Double, cellMaxY As Double
    Dim eCx As Double, eCy As Double
    Dim txt As String, newTxt As String
    Dim txtEnt As AcadText
    Dim mtxtEnt As AcadMText
    Dim unlabeledCounter As Long
    unlabeledCounter = 0
    
    For i = 1 To UBound(labels)
        If i > centers.count Then Exit For
        
        Dim currentLabel As String
        currentLabel = Trim$(labels(i))
        If currentLabel = "" Then
            unlabeledCounter = unlabeledCounter + 1
            currentLabel = "SEM GRAVAÇÃO " & Format(unlabeledCounter, "00")
        End If
        
        centerPt = centers(i)
        cellMinX = centerPt(0) - cellWidth / 2
        cellMaxX = centerPt(0) + cellWidth / 2
        cellMinY = centerPt(1) - cellHeight / 2
        cellMaxY = centerPt(1) + cellHeight / 2
        
        ' Search for text entities inside this cell that contain the placeholder "XXXX"
        For Each ent In gridSS
            If TypeOf ent Is AcadText Or TypeOf ent Is AcadMText Then
                On Error Resume Next
                ent.GetBoundingBox eMin, eMax
                If Err.Number = 0 Then
                    eCx = (eMin(0) + eMax(0)) / 2
                    eCy = (eMin(1) + eMax(1)) / 2
                    If eCx >= cellMinX And eCx <= cellMaxX And _
                       eCy >= cellMinY And eCy <= cellMaxY Then
                        txt = GetEntityTextString(ent)
                        If InStr(1, txt, "XXXX", vbBinaryCompare) > 0 Then
                            newTxt = Replace(txt, "XXXX", currentLabel, 1, -1, vbBinaryCompare)
                            If TypeOf ent Is AcadText Then
                                Set txtEnt = ent
                                txtEnt.TextString = newTxt
                            ElseIf TypeOf ent Is AcadMText Then
                                Set mtxtEnt = ent
                                mtxtEnt.TextString = newTxt
                            End If
                        End If
                    End If
                End If
                Err.Clear
                On Error GoTo 0
            End If
        Next ent
    Next i
End Sub

Private Sub VisualizeGridCenters(doc As AcadDocument, centers As collection, xGrid() As Double, Optional pointColor As Long = acRed, Optional debugLabel As String = "")
    ' Draw points at grid cell centers with hyperlink metadata containing cell coordinates
    ' pointColor: color for the points (default acRed)
    ' debugLabel: optional label prefix for hyperlink descriptions (e.g., "Before Scaling", "After Scaling")
    On Error Resume Next
    Dim i As Long
    Dim pt As Variant
    Dim cols As Long
    Dim cellIndex As Long
    Dim row As Long, col As Long
    Dim label As String
    Dim hyperLabel As String
    Dim pointObj As Object
    
    cols = UBound(xGrid)
    
    For i = 1 To centers.count
        pt = centers(i)
        
        ' Calculate row and column from index
        cellIndex = i - 1
        row = cellIndex \ cols
        col = cellIndex Mod cols
        
        ' Format label as R##C##
        label = "R" & Format(row + 1, "00") & "C" & Format(col + 1, "00")
        
        ' Include debug label in hyperlink description if provided
        If debugLabel <> "" Then
            hyperLabel = debugLabel & " - " & label
        Else
            hyperLabel = label
        End If
        
        ' Create point at grid center
        Set pointObj = doc.modelSpace.AddPoint(pt)
        
        ' Set color and add hyperlink metadata
        If Not pointObj Is Nothing Then
            pointObj.Color = pointColor
            pointObj.layer = "Shapes"
            
            ' Add hyperlink metadata with cell coordinate information
            If pointObj.Hyperlinks.count >= 0 Then
                pointObj.Hyperlinks.Add hyperLabel
                pointObj.Hyperlinks(1).Description = hyperLabel
            End If
        End If
        
        Err.Clear
    Next i
    
    doc.Application.Refresh
    Err.Clear
    On Error GoTo 0
End Sub

'-----------------------------
' Geometry collection helpers (borrowed from autoOrient)
'-----------------------------

Private Sub AddPoint(X As Double, Y As Double, ByRef points() As Point2D, ByRef count As Long)
    If count > UBound(points) Then ReDim Preserve points(0 To UBound(points) * 2) As Point2D
    points(count).X = X
    points(count).Y = Y
    count = count + 1
End Sub

Private Sub CollectRegionPoints(ent As AcadEntity, centerPt() As Double, ByRef points() As Point2D, ByRef count As Long)
    On Error Resume Next
    Dim exploded As Variant
    exploded = ent.Explode
    If Err.Number <> 0 Or IsEmpty(exploded) Then
        Err.Clear
        CollectBoundingBoxPoints ent, centerPt, points, count
        Exit Sub
    End If
    Dim i As Long
    Dim subEnt As AcadEntity
    For i = LBound(exploded) To UBound(exploded)
        Set subEnt = exploded(i)
        Dim nm As String
        nm = UCase$(subEnt.ObjectName)
        If InStr(1, nm, "REGION", vbTextCompare) > 0 Then
            CollectBoundingBoxPoints subEnt, centerPt, points, count
        ElseIf InStr(1, nm, "LINE", vbTextCompare) > 0 Then
            CollectLinePoints subEnt, centerPt, points, count
        ElseIf InStr(1, nm, "ARC", vbTextCompare) > 0 Then
            CollectArcPoints subEnt, centerPt, points, count
        Else
            CollectBoundingBoxPoints subEnt, centerPt, points, count
        End If
        subEnt.Delete
    Next i
    On Error GoTo 0
End Sub

Private Sub CollectPolylinePoints(ent As AcadEntity, centerPt() As Double, ByRef points() As Point2D, ByRef count As Long)
    On Error Resume Next
    Dim exploded As Variant
    exploded = ent.Explode
    If Err.Number <> 0 Or IsEmpty(exploded) Then
        Err.Clear
        CollectBoundingBoxPoints ent, centerPt, points, count
        Exit Sub
    End If
    Dim i As Long
    Dim subEnt As AcadEntity
    For i = LBound(exploded) To UBound(exploded)
        Set subEnt = exploded(i)
        Dim nm As String
        nm = UCase$(subEnt.ObjectName)
        If InStr(1, nm, "LINE", vbTextCompare) > 0 Then
            CollectLinePoints subEnt, centerPt, points, count
        ElseIf InStr(1, nm, "ARC", vbTextCompare) > 0 Then
            CollectArcPoints subEnt, centerPt, points, count
        Else
            CollectBoundingBoxPoints subEnt, centerPt, points, count
        End If
        subEnt.Delete
    Next i
    On Error GoTo 0
End Sub

Private Sub CollectLinePoints(lineEnt As AcadEntity, centerPt() As Double, ByRef points() As Point2D, ByRef count As Long)
    On Error Resume Next
    Dim sp As Variant, ep As Variant
    sp = lineEnt.startPoint
    ep = lineEnt.endPoint
    AddPoint sp(0) - centerPt(0), sp(1) - centerPt(1), points, count
    AddPoint ep(0) - centerPt(0), ep(1) - centerPt(1), points, count
    On Error GoTo 0
End Sub

Private Sub CollectArcPoints(arcEnt As AcadEntity, centerPt() As Double, ByRef points() As Point2D, ByRef count As Long)
    On Error Resume Next
    Dim sp As Variant, ep As Variant
    sp = arcEnt.startPoint
    ep = arcEnt.endPoint
    AddPoint sp(0) - centerPt(0), sp(1) - centerPt(1), points, count
    AddPoint ep(0) - centerPt(0), ep(1) - centerPt(1), points, count
    Dim radius As Double, cen As Variant, sa As Double, ea As Double
    radius = arcEnt.radius
    cen = arcEnt.center
    sa = arcEnt.startAngle
    ea = arcEnt.endAngle
    Dim diff As Double
    diff = ea - sa
    If diff <= 0 Then diff = diff + 6.28318530717959
    Dim mid As Double
    mid = sa + diff / 2
    Dim mx As Double, my As Double
    mx = cen(0) + radius * Cos(mid)
    my = cen(1) + radius * Sin(mid)
    AddPoint mx - centerPt(0), my - centerPt(1), points, count
    On Error GoTo 0
End Sub

Private Sub CollectBoundingBoxPoints(ent As AcadEntity, centerPt() As Double, ByRef points() As Point2D, ByRef count As Long)
    On Error Resume Next
    Dim minPt As Variant, maxPt As Variant
    ent.GetBoundingBox minPt, maxPt
    If Err.Number = 0 Then
        AddPoint minPt(0) - centerPt(0), minPt(1) - centerPt(1), points, count
        AddPoint maxPt(0) - centerPt(0), minPt(1) - centerPt(1), points, count
        AddPoint maxPt(0) - centerPt(0), maxPt(1) - centerPt(1), points, count
        AddPoint minPt(0) - centerPt(0), maxPt(1) - centerPt(1), points, count
    End If
    On Error GoTo 0
End Sub

Private Sub GetRotatedBoundsFromPoints(points() As Point2D, count As Long, angle As Double, ByRef widthOut As Double, ByRef heightOut As Double)
    Const LARGE As Double = 1E+30
    Dim minX As Double: minX = LARGE
    Dim minY As Double: minY = LARGE
    Dim maxX As Double: maxX = -LARGE
    Dim maxY As Double: maxY = -LARGE
    Dim cosA As Double: cosA = Cos(angle)
    Dim sinA As Double: sinA = Sin(angle)
    Dim i As Long, rx As Double, ry As Double
    For i = 0 To count - 1
        rx = points(i).X * cosA - points(i).Y * sinA
        ry = points(i).X * sinA + points(i).Y * cosA
        If rx < minX Then minX = rx
        If rx > maxX Then maxX = rx
        If ry < minY Then minY = ry
        If ry > maxY Then maxY = ry
    Next i
    If minX > maxX Then
        widthOut = 0: heightOut = 0
    Else
        widthOut = maxX - minX
        heightOut = maxY - minY
    End If
End Sub

'-----------------------------
' Utilities
'-----------------------------

Private Function ExtractRegionLabel(ents As collection) As String
    Dim ent As AcadEntity
    For Each ent In ents
        If TypeOf ent Is AcadText Or TypeOf ent Is AcadMText Then
            If IsGravacaoLayerName(ent.layer) Then
                Dim txt As String
                txt = Trim$(GetEntityTextString(ent))
                If txt <> "" Then
                    If Not ContainsExcludedKeyword(txt) Then
                        ExtractRegionLabel = txt
                        Exit Function
                    End If
                End If
            End If
        End If
    Next ent
End Function

Private Function GetEntityTextString(ent As AcadEntity) As String
    On Error Resume Next
    If TypeOf ent Is AcadText Then
        GetEntityTextString = ent.TextString
    ElseIf TypeOf ent Is AcadMText Then
        GetEntityTextString = ent.TextString
    End If
    Err.Clear
    On Error GoTo 0
End Function

Private Function IsGravacaoLayerName(layerName As String) As Boolean
    Dim normalized As String
    normalized = LCase$(StripDiacritics(Trim$(layerName)))
    IsGravacaoLayerName = (normalized = "gravacao")
End Function

Private Function ContainsExcludedKeyword(textVal As String) As Boolean
    Dim normalized As String
    normalized = LCase$(StripDiacritics(Trim$(textVal)))
    If normalized = "carroceria" Then ContainsExcludedKeyword = True: Exit Function
    If normalized = "ferramentaria" Then ContainsExcludedKeyword = True: Exit Function
    If normalized = "portas" Then ContainsExcludedKeyword = True: Exit Function
    If normalized = "tampa" Then ContainsExcludedKeyword = True: Exit Function
    If normalized = "vidros" Then ContainsExcludedKeyword = True: Exit Function
    If normalized = "teto" Then ContainsExcludedKeyword = True: Exit Function
    If normalized = "carrinho" Then ContainsExcludedKeyword = True: Exit Function
End Function

Private Function OrderRegionsByLabel(regionEntities As collection, ByRef labels() As String) As collection
    Dim labeled As New collection
    Dim unlabeled As New collection
    Dim i As Long
    For i = 1 To regionEntities.count
        If Trim$(labels(i)) <> "" Then
            labeled.Add i
        Else
            unlabeled.Add i
        End If
    Next i

    ' Sort all labeled indices alphabetically so duplicate detection is in label order
    Dim sortedLabeled As collection
    Set sortedLabeled = SortIndicesByLabel(labels, labeled)

    ' Split into: first occurrence of each label vs. subsequent (duplicate) occurrences.
    ' Duplicates are pushed after unlabeled shapes at the end.
    Dim firstOccurrence As New collection
    Dim duplicates As New collection
    Dim seenLabels() As String
    Dim seenCount As Long
    seenCount = 0
    If labeled.count > 0 Then ReDim seenLabels(1 To labeled.count)

    Dim idxVar As Variant
    For Each idxVar In sortedLabeled
        Dim lbl As String
        lbl = labels(CLng(idxVar))
        Dim alreadySeen As Boolean
        alreadySeen = False
        Dim s As Long
        For s = 1 To seenCount
            If StrComp(seenLabels(s), lbl, vbTextCompare) = 0 Then
                alreadySeen = True
                Exit For
            End If
        Next s
        If alreadySeen Then
            duplicates.Add idxVar
        Else
            seenCount = seenCount + 1
            seenLabels(seenCount) = lbl
            firstOccurrence.Add idxVar
        End If
    Next idxVar

    Dim result As New collection
    Dim newLabels() As String
    ReDim newLabels(LBound(labels) To UBound(labels))
    Dim k As Long
    k = LBound(labels)

    ' Order: unique first occurrences (A-Z) ? unlabeled ? duplicate occurrences (A-Z)
    For Each idxVar In firstOccurrence
        result.Add regionEntities(idxVar)
        newLabels(k) = labels(idxVar)
        k = k + 1
    Next idxVar
    For Each idxVar In unlabeled
        result.Add regionEntities(idxVar)
        newLabels(k) = labels(idxVar)
        k = k + 1
    Next idxVar
    For Each idxVar In duplicates
        result.Add regionEntities(idxVar)
        newLabels(k) = labels(idxVar)
        k = k + 1
    Next idxVar

    labels = newLabels
    Set OrderRegionsByLabel = result
End Function

Private Function SortIndicesByLabel(labels() As String, indices As collection) As collection
    Dim count As Long
    count = indices.count
    If count = 0 Then
        Dim emptyCol As New collection
        Set SortIndicesByLabel = emptyCol
        Exit Function
    End If
    Dim arr() As Long
    ReDim arr(1 To count)
    Dim i As Long, j As Long
    For i = 1 To count
        arr(i) = CLng(indices(i))
    Next i
    For i = 1 To count - 1
        For j = i + 1 To count
            If StrComp(labels(arr(i)), labels(arr(j)), vbTextCompare) > 0 Then
                Dim tmp As Long
                tmp = arr(i)
                arr(i) = arr(j)
                arr(j) = tmp
            End If
        Next j
    Next i
    Dim sorted As New collection
    For i = 1 To count
        sorted.Add arr(i)
    Next i
    Set SortIndicesByLabel = sorted
End Function

Private Function PrepareSelectionSet(doc As AcadDocument, name As String) As AcadSelectionSet
    On Error Resume Next
    Dim ss As AcadSelectionSet
    Set ss = doc.SelectionSets.item(name)
    If Err.Number = 0 Then
        ss.Clear
    Else
        Err.Clear
        Set ss = doc.SelectionSets.Add(name)
    End If
    On Error GoTo 0
    Set PrepareSelectionSet = ss
End Function

Private Sub NormalizeSelectedLayers(ss As AcadSelectionSet)
    Dim ent As AcadEntity
    For Each ent In ss
        Dim layerName As String
        layerName = LCase$(StripDiacritics(Trim$(ent.layer)))
        If InStr(1, layerName, "gravacao", vbTextCompare) = 0 And _
            InStr(1, layerName, "texto", vbTextCompare) = 0 And _
           InStr(1, layerName, "dobra", vbTextCompare) = 0 Then
            On Error Resume Next
            If ent.Color = acYellow Then
                EnsureGravacaoLayer ThisDrawing
                ent.layer = "Gravação"
                ent.Color = acByLayer
            Else
                ent.layer = "0"
                ent.Color = acByLayer
            End If
            Err.Clear
            On Error GoTo 0
        End If
    Next ent
End Sub

Private Function StripDiacritics(ByVal text As String) As String
    Dim i As Long
    Dim ch As String
    Dim code As Long
    Dim result As String
    result = ""
    For i = 1 To Len(text)
        ch = mid$(text, i, 1)
        code = AscW(ch)
        Select Case code
            Case 192, 193, 194, 195, 196, 197, 224, 225, 226, 227, 228, 229
                result = result & "a"
            Case 199, 231
                result = result & "c"
            Case 200, 201, 202, 203, 232, 233, 234, 235
                result = result & "e"
            Case 204, 205, 206, 207, 236, 237, 238, 239
                result = result & "i"
            Case 210, 211, 212, 213, 214, 242, 243, 244, 245, 246
                result = result & "o"
            Case 217, 218, 219, 220, 249, 250, 251, 252
                result = result & "u"
            Case Else
                result = result & ch
        End Select
    Next i
    StripDiacritics = result
End Function

Private Function EnsureShapesLayer(doc As AcadDocument) As AcadLayer
    Dim shapesLayer As AcadLayer
    On Error Resume Next
    Set shapesLayer = doc.layers.item("Shapes")
    If Err.Number <> 0 Then
        Err.Clear
        Set shapesLayer = doc.layers.Add("Shapes")
        shapesLayer.Color = acGreen
    End If
    On Error GoTo 0
    Set EnsureShapesLayer = shapesLayer
End Function

Private Function EnsureGravacaoLayer(doc As AcadDocument) As AcadLayer
    Dim gravLayer As AcadLayer
    On Error Resume Next
    Set gravLayer = doc.layers.item("Gravação")
    If Err.Number <> 0 Then
        Err.Clear
        Set gravLayer = doc.layers.Add("Gravação")
        gravLayer.Color = acYellow
    End If
    On Error GoTo 0
    Set EnsureGravacaoLayer = gravLayer
End Function

'-----------------------------
' Export shapes to DWG files
'-----------------------------

Public Sub ExportShapesToDxf(regionEntities As collection, regionLabels() As String)
    On Error GoTo ErrHandler
    
    If MsgBox("Deseja salvar cada forma como um arquivo DXF separado?", _
              vbYesNo + vbQuestion, "Exportar Formas") = vbNo Then
        Exit Sub
    End If
    
    Dim destFolder As String
    destFolder = BrowseForFolderDialog("Selecione a pasta de destino para os arquivos DXF")
    If Trim$(destFolder) = "" Then
        MsgBox "Nenhuma pasta selecionada. Exportação cancelada.", vbInformation, "Exportar Formas"
        Exit Sub
    End If
    If Right$(destFolder, 1) <> "\" Then destFolder = destFolder & "\"
    
    Dim doc As AcadDocument
    Set doc = ThisDrawing
    
    Dim exported As Long
    exported = 0
    Dim unlabeledCounter As Long
    unlabeledCounter = 0
    Dim i As Long
    For i = 1 To regionEntities.count
        Dim label As String
        label = ""
        If i <= UBound(regionLabels) Then label = Trim$(regionLabels(i))
        If label = "" Then
            unlabeledCounter = unlabeledCounter + 1
            label = "SEM GRAVAÇÃO " & Format(unlabeledCounter, "00")
        End If
        label = SanitizeFileName(label)
        
        Dim dxfPath As String
        Dim tmpPath As String
        dxfPath = destFolder & label & ".dxf"
        tmpPath = destFolder & label & "_tmp.dwg"
        
        Dim ents As collection
        Set ents = regionEntities(i)
        If ents.count = 0 Then GoTo NextShape
        
        ' Only export entities on layer "0" or "Gravação" — skips regions on the "Shapes" layer
        Dim exportEnts As collection
        Set exportEnts = New collection
        Dim entObj As AcadEntity
        For Each entObj In ents
            Dim layerNorm As String
            layerNorm = LCase$(StripDiacritics(entObj.layer))
            If layerNorm = "0" Or layerNorm = "gravacao" Then
                exportEnts.Add entObj
            End If
        Next entObj
        If exportEnts.count = 0 Then GoTo NextShape
        
        ' Bounding-box center of the entities to export
        Dim minPt As Variant, maxPt As Variant
        GetEntitiesBounds exportEnts, minPt, maxPt
        Dim cx As Double, cy As Double
        cx = (minPt(0) + maxPt(0)) / 2
        cy = (minPt(1) + maxPt(1)) / 2
        
        ' Temporarily move entities to origin
        Dim fromPt(0 To 2) As Double
        Dim toPt(0 To 2) As Double
        fromPt(0) = cx: fromPt(1) = cy: fromPt(2) = 0
        toPt(0) = 0: toPt(1) = 0: toPt(2) = 0
        MoveEntities exportEnts, fromPt, toPt
        
        ' Build a temporary selection set and write to file with Wblock
        Dim wbSS As AcadSelectionSet
        Set wbSS = PrepareSelectionSet(doc, "DSG_WBLOCK")
        For Each entObj In exportEnts
            On Error Resume Next
            wbSS.AddItems Array(entObj)
            Err.Clear
            On Error GoTo ErrHandler
        Next entObj
        
        On Error Resume Next
        doc.Wblock tmpPath, wbSS
        Dim wblockOk As Boolean
        wblockOk = (Err.Number = 0) And (Dir(tmpPath) <> "")
        Err.Clear
        wbSS.Delete
        Err.Clear
        On Error GoTo ErrHandler
        
        ' Restore entities to their original position
        MoveEntities exportEnts, toPt, fromPt
        
        If wblockOk Then
            ' Open the temp DWG, then use SendCommand to run -DXFOUT directly on that document.
            ' Application.Eval runs in the wrong document context; SendCommand targets exportedDoc.
            ' FILEDIA is suppressed so no file-picker dialog interrupts the batch export.
            Dim exportedDoc As AcadDocument
            On Error Resume Next
            Set exportedDoc = Application.Documents.Open(tmpPath)
            If Err.Number = 0 And Not exportedDoc Is Nothing Then
                DoEvents  ' let the document become active
                ' exportedDoc.SendCommand "ZOOMANIM" & vbCr & "0" & vbCr
                exportedDoc.Application.ZoomExtents
                exportedDoc.SendCommand _
                    "FILEDIA" & vbCr & "0" & vbCr & _
                    "DXFOUT" & vbCr & dxfPath & vbCr & "16" & vbCr & _
                    "FILEDIA" & vbCr & "1" & vbCr
                ' Wait up to 15 seconds for the DXF file to appear on disk
                Dim waitStart As Single
                waitStart = Timer
                Do
                    DoEvents
                Loop Until Dir(dxfPath) <> "" Or (Timer - waitStart > 15)
                exportedDoc.Close False
            End If
            Err.Clear
            ' Delete the temp DWG, its .bak, and any .bak BricsCAD creates alongside the DXF
            Dim bakPath As String
            bakPath = Left$(tmpPath, Len(tmpPath) - 4) & ".bak"
            DeleteFileWithRetry bakPath
            DeleteFileWithRetry tmpPath
            DeleteFileWithRetry Left$(dxfPath, Len(dxfPath) - 4) & ".bak"
            Err.Clear
            Set exportedDoc = Nothing
            On Error GoTo ErrHandler
            ' Only count as exported if the DXF file was actually created on disk
            If Dir(dxfPath) <> "" Then exported = exported + 1
        End If
NextShape:
    Next i
    
    MsgBox exported & " forma(s) exportada(s) como DXF com sucesso para:" & vbCr & destFolder, _
           vbInformation, "Exportar Formas"
    Exit Sub
    
ErrHandler:
    MsgBox "Erro ao exportar formas: " & Err.Description, vbCritical, "Exportar Formas"
End Sub

Private Sub DeleteFileWithRetry(filePath As String)
    Const MAX_TRIES As Long = 5
    Dim attempt As Long
    For attempt = 1 To MAX_TRIES
        On Error Resume Next
        If Dir(filePath) <> "" Then
            Kill filePath
        End If
        If Err.Number = 0 And Dir(filePath) = "" Then
            Err.Clear
            On Error GoTo 0
            Exit Sub  ' successfully deleted (or never existed)
        End If
        Err.Clear
        On Error GoTo 0
        DoEvents  ' yield briefly so the OS can release any file lock
        DoEvents
        DoEvents
     Next attempt
    On Error Resume Next
    If Dir(filePath) <> "" Then Kill filePath  ' final attempt
    Err.Clear
    On Error GoTo 0
End Sub

Private Function BrowseForFolderDialog(title As String) As String
    On Error GoTo Fallback
    Dim shell As Object
    Set shell = CreateObject("Shell.Application")
    Dim folder As Object
    Set folder = shell.BrowseForFolder(0, title, 0, 0)
    If Not folder Is Nothing Then
        BrowseForFolderDialog = folder.Self.path
    End If
    Exit Function
Fallback:
    Err.Clear
    BrowseForFolderDialog = InputBox("Digite o caminho da pasta de destino:", title, "C:\")
End Function

Private Function SanitizeFileName(ByVal name As String) As String
    Dim invalid As String
    invalid = "\/:*?""<>|"
    Dim i As Long
    For i = 1 To Len(invalid)
        name = Join(Split(name, mid$(invalid, i, 1)), "_")
    Next i
    SanitizeFileName = Trim$(name)
End Function

Attribute VB_Name = "M_explodeDobrasMText"
Option Explicit

'================================================================================
' Module : explodeMText.vba
' Purpose: Iterate all MText objects on layers "Texto" and "Dobras", strip their
'          MText formatting codes, then explode each one into a single plain
'          Text (DText) entity.
'
' Problem solved:
'   Raw MText content such as:
'     \A1;{\fCalibri|b0|i0|c0|p34;DS 65\H0.7x;\SO^;}
'   contains two formatting "runs" (normal height text + smaller-height stacked
'   text for the degree sign).  Exploding that MText directly yields TWO separate
'   Text objects: one with "DS 65" and one with the degree character "°".
'
'   This module first rewrites the TextString to plain text (one single run),
'   so that explosion always produces exactly ONE Text object per MText.
'
' Reference: mText.vba  – handle-based _SELECT + _EXPLODE approach.
'================================================================================


'--------------------------------------------------------------------------------
' ExplodeMText_TexDobras  (entry point – call this from VBARUN)
'
' Layers processed: "Texto" and "Dobras"
'--------------------------------------------------------------------------------
Public Sub ExplodeMText_TexDobras()

    Dim acadDoc    As Object   ' AcadDocument / ThisDrawing
    Dim modelSpace As Object   ' AcadModelSpace
    Dim entity     As Object   ' generic loop iterator
    Dim mtextObj   As Object   ' current MText entity
    Dim mtextList  As collection
    Dim i          As Long
    Dim cleanText  As String
    Dim processed  As Long

    On Error GoTo ErrorHandler

    Set acadDoc = ThisDrawing
    Set modelSpace = acadDoc.modelSpace

    ' -- Step 1: collect every MText on the target layers ---------------------
    Set mtextList = New collection

    For Each entity In modelSpace
        If entity.ObjectName = "AcDbMText" Then
            If entity.layer = "Texto" Or entity.layer = "Dobras" Then
                mtextList.Add entity
            End If
        End If
    Next entity

    If mtextList.count = 0 Then
        MsgBox "Nenhum MText encontrado nas camadas 'Texto' ou 'Dobras'.", _
               vbInformation, "ExplodeMText"
        GoTo Cleanup
    End If

    ' -- Step 2: simplify TextString then explode each MText ------------------
    processed = 0

    For i = 1 To mtextList.count
        Set mtextObj = mtextList(i)

        On Error Resume Next

        ' Strip all MText formatting codes.
        ' \SO^;  ?  "°"  (degree-sign idiom used in these drawings).
        ' All other codes (font, height, alignment, etc.) are removed.
        cleanText = SimplifyMTextRaw(mtextObj.TextString)

        ' Overwrite the TextString with the plain, single-run result.
        ' After this call the MText has no height changes mid-string,
        ' so explosion will yield exactly one Text entity.
        mtextObj.TextString = cleanText
        mtextObj.Update

        If Err.Number <> 0 Then
            Debug.Print "Simplify failed  handle=" & mtextObj.Handle & _
                        "  err=" & Err.Description
            Err.Clear
        Else
            ' Explode using the same handle-based pattern as mText.vba
            Dim explodeCmd As String
            explodeCmd = "_SELECT (handent """ & mtextObj.Handle & """) " & vbCr & _
                         "_EXPLODE " & vbCr
            acadDoc.SendCommand explodeCmd

            If Err.Number = 0 Then
                processed = processed + 1
            Else
                Debug.Print "Explode failed  handle=" & mtextObj.Handle & _
                            "  err=" & Err.Description
                Err.Clear
            End If
        End If

        On Error GoTo ErrorHandler
    Next i

    ' Allow BricsCAD to finish processing the last commands before refreshing
    Wait 0.5
    acadDoc.Regen acAllViewports

    MsgBox processed & " de " & mtextList.count & _
           " objeto(s) MText convertido(s) para Text com sucesso.", _
           vbInformation, "ExplodeMText"

Cleanup:
    Set acadDoc = Nothing
    Set modelSpace = Nothing
    Set mtextList = Nothing
    Set entity = Nothing
    Set mtextObj = Nothing
    Exit Sub

ErrorHandler:
    MsgBox "Erro: " & Err.Description & vbCrLf & "(Código " & Err.Number & ")", _
           vbCritical, "ExplodeMText"
    Resume Cleanup

End Sub


'================================================================================
' SimplifyMTextRaw
'
' Strips BricsCAD / AutoCAD MText inline formatting codes from a raw TextString
' and returns a clean, printable string suitable for a plain Text entity.
'
' Conversion table (applied in order):
'
'   \SO^;  or  \So^;          ?  "°"   degree-sign idiom (superscript O)
'   \S…;   (any remaining)    ?  ""    other stacked / fraction text removed
'   \f…;   \F…;               ?  ""    font change
'   \A[n];                    ?  ""    alignment
'   \H[n]x; or \H[n];         ?  ""    character height multiplier
'   \W[n];                    ?  ""    width factor
'   \Q[n];                    ?  ""    oblique angle
'   \T[n];                    ?  ""    tracking
'   \C[n];                    ?  ""    colour index
'   \p…;                      ?  ""    paragraph properties
'   \L \l \O \o \K \k          ?  ""    under/over-line and strikethrough toggles
'   \P                         ?  " "   paragraph break ? space
'   %%d  %%D                   ?  "°"  alternate degree control code
'   {  }                       ?  ""    group delimiters
'================================================================================
Private Function SimplifyMTextRaw(ByVal rawStr As String) As String

    Dim s  As String
    Dim re As Object

    s = rawStr
    Set re = CreateObject("VBScript.RegExp")
    re.Global = True
    re.IgnoreCase = True    ' treat upper/lower the same for all letter-based codes

    ' -- Degree-sign idiom: \SO^; or \So^;  ?  "°" ----------------------------
    ' This MUST be done before the general \S handler and before the \O toggle
    ' handler, otherwise the "O" inside \SO^; would be consumed by those steps.
    '
    ' Pattern breakdown (VBScript regex):
    '   \\S  – literal backslash + S   (matches the \S in the raw string)
    '   O    – letter O (case-insensitive: also matches o)
    '   \^   – literal caret character  (the stacking separator)
    '   [^;]* – anything up to the closing semicolon
    '   ;    – closing semicolon
    re.Pattern = "\\SO\^[^;]*;"
    s = re.Replace(s, Chr(176))         ' Chr(176) = U+00B0 DEGREE SIGN  "°"

    ' -- Remaining stacked text: \S…;  ?  remove ------------------------------
    ' Any \S not already replaced above (fractions, other stacks) is dropped.
    re.Pattern = "\\S[^;]+;"
    s = re.Replace(s, "")

    ' -- Font code: \fCalibri|b0|i0|c0|p34;  ?  remove -----------------------
    re.Pattern = "\\[fF][^;]*;"
    s = re.Replace(s, "")

    ' -- Alignment: \A1;  ?  remove -------------------------------------------
    re.Pattern = "\\A\d+;"
    s = re.Replace(s, "")

    ' -- Character height: \H0.7x;  or  \H2.5;  ?  remove --------------------
    re.Pattern = "\\H[\d.]+[xX]?;"
    s = re.Replace(s, "")

    ' -- Width factor: \W1.2;  ?  remove -------------------------------------
    re.Pattern = "\\W[\d.]+;"
    s = re.Replace(s, "")

    ' -- Oblique angle: \Q15;  ?  remove -------------------------------------
    re.Pattern = "\\Q[\d.]+;"
    s = re.Replace(s, "")

    ' -- Tracking: \T1.2;  ?  remove -----------------------------------------
    re.Pattern = "\\T[\d.]+;"
    s = re.Replace(s, "")

    ' -- Colour index: \C2;  ?  remove ----------------------------------------
    re.Pattern = "\\C\d+;"
    s = re.Replace(s, "")

    ' -- Paragraph properties: \pi1,l1,ql;  ?  remove ------------------------
    re.Pattern = "\\p[^;]*;"
    s = re.Replace(s, "")

    ' -- Inline toggles (no closing semicolon): \L \l \O \o \K \k ------------
    ' \L/\l = underline on/off,  \O/\o = overline on/off,  \K/\k = strikethrough on/off
    ' NOTE: \O toggle is safe here because \SO^; was already handled above.
    re.Pattern = "\\[LlOoKk]"
    s = re.Replace(s, "")

    ' -- Paragraph break: \P  ?  space ----------------------------------------
    re.Pattern = "\\P"
    s = re.Replace(s, " ")

    ' -- Legacy degree control code: %%d  ?  "°" -----------------------------
    s = Replace(s, "%%d", Chr(176))
    s = Replace(s, "%%D", Chr(176))

    ' -- Remove { } group delimiters ------------------------------------------
    s = Replace(s, "{", "")
    s = Replace(s, "}", "")

    ' -- Collapse any resulting runs of whitespace -----------------------------
    re.Pattern = "\s+"
    s = re.Replace(s, " ")

    SimplifyMTextRaw = Trim(s)

End Function


'--------------------------------------------------------------------------------
' Wait – yield control for the given number of seconds
'--------------------------------------------------------------------------------
Private Sub Wait(seconds As Double)
    Dim t As Double
    t = Timer
    Do While Timer < t + seconds
        DoEvents
    Loop
End Sub


' ================================================================================
' HOW TO USE
' ================================================================================
' 1. Open BricsCAD and the target drawing.
' 2. Press ALT+F11 to open the VBA IDE (or type VBAIDE in the command line).
' 3. Go to File > Import File... and select this file (explodeMText.vba),
'    OR go to Insert > Module and paste this code into the new module.
' 4. Close the VBA IDE.
' 5. In BricsCAD, type VBARUN in the command line.
' 6. Select "ExplodeMText_TexDobras" from the list and click Run.
'
' WHAT IT DOES
' -------------
' For every MText on layers "Texto" and "Dobras" the macro will:
'   a) Read the raw TextString  (e.g.  \A1;{\fCalibri|b0|i0|c0|p34;DS 65\H0.7x;\SO^;})
'   b) Strip all formatting codes and convert the degree-sign idiom to "°"
'      ? result:  DS 65°
'   c) Write the plain text back to the MText object (now a single formatting run)
'   d) Explode the MText via EXPLODE command
'      ? result:  ONE regular Text entity containing "DS 65°"
' ================================================================================

Attribute VB_Name = "M_scaleToTextSize"
Option Explicit

' Scales a user selection so that its largest single-line text height
' matches a user-supplied target height (in mm).
'
' Supported text types for height detection: AcDbText, AcDbAttribute,
' AcDbAttributeDefinition.  MText (AcDbMText) is intentionally skipped
' because its .Height property returns the bounding-box height, not the
' individual character height.

Public Sub ScaleToTextSize()
    Dim doc As AcadDocument
    Dim ss As AcadSelectionSet
    Dim ent As AcadEntity
    Dim i As Long
    Dim h As Double
    Dim maxTextHeight As Double
    Dim targetHeight As Double
    Dim scaleFactor As Double
    Dim bboxMin As Variant
    Dim bboxMax As Variant
    Dim totalMinPt(0 To 2) As Double
    Dim totalMaxPt(0 To 2) As Double
    Dim centerPt(0 To 2) As Double
    Dim firstEnt As Boolean
    Dim formWasVisible As Boolean
    Dim strTarget As String
    Dim lastTargetHeight As Double
    Dim meanTextHeight As Double
    Dim textCount As Long

    Set doc = ThisDrawing

    ' ---------- 0. Hide userform so it does not block the viewport ----------
    formWasVisible = False
    On Error Resume Next
    formWasVisible = formPerfisul01.Visible
    If formWasVisible Then formPerfisul01.Hide
    On Error GoTo 0

    ' ---------- Main loop: repeat until user cancels ----------
    Do
        ' ----- 1. Prompt user to area-select objects -----
        On Error Resume Next
        doc.SelectionSets("STS_SS").Delete
        On Error GoTo 0

        Set ss = doc.SelectionSets.Add("STS_SS")
        doc.Utility.prompt vbCr & "Select objects to scale (empty selection to exit): "
        ss.SelectOnScreen

        If ss.count = 0 Then
            ss.Delete
            Exit Do
        End If

        ' ----- 2. Find the largest text height in the selection -----
        maxTextHeight = 0
        meanTextHeight = 0
        textCount = 0
        For i = 0 To ss.count - 1
            Set ent = ss.item(i)
            h = 0
            Select Case ent.ObjectName
                Case "AcDbText", "AcDbAttribute", "AcDbAttributeDefinition"
                    On Error Resume Next
                    h = ent.height
                    On Error GoTo 0
            End Select
            If h > 0 Then
                If h > maxTextHeight Then maxTextHeight = h
                meanTextHeight = meanTextHeight + h
                textCount = textCount + 1
            End If
        Next i
        If textCount > 0 Then meanTextHeight = meanTextHeight / textCount

        If maxTextHeight = 0 Then
            MsgBox "No text objects (TEXT / ATTDEF / ATTRIB) found in selection." & vbCr & _
                   "Please select again.", vbExclamation
            ss.Delete

        Else
            ' ----- 3. Prompt for target text height (InputBox) -----
            Dim defaultHeight As Double
            If lastTargetHeight > 0 Then
                defaultHeight = lastTargetHeight
            Else
                defaultHeight = meanTextHeight
            End If
            strTarget = InputBox( _
                "Largest text height found:  " & Format(maxTextHeight, "0.####") & " mm" & vbCr & vbCr & _
                "Enter the target text height (mm):", _
                "Scale to Text Size", _
                Format(defaultHeight, "0.####"))

            If strTarget = "" Then
                ' User cancelled the dialog
                ss.Delete
                Exit Do
            End If

            On Error Resume Next
            targetHeight = CDbl(strTarget)
            If Err.Number <> 0 Or targetHeight <= 0 Then
                On Error GoTo 0
                MsgBox "Invalid value. Please enter a number greater than zero.", vbExclamation
                ss.Delete

            Else
                On Error GoTo 0

                ' ----- 4. Compute the bounding-box centre of the full selection -----
                firstEnt = True
                For i = 0 To ss.count - 1
                    Set ent = ss.item(i)
                    On Error Resume Next
                    ent.GetBoundingBox bboxMin, bboxMax
                    If Err.Number = 0 Then
                        If firstEnt Then
                            totalMinPt(0) = bboxMin(0): totalMinPt(1) = bboxMin(1): totalMinPt(2) = 0
                            totalMaxPt(0) = bboxMax(0): totalMaxPt(1) = bboxMax(1): totalMaxPt(2) = 0
                            firstEnt = False
                        Else
                            If bboxMin(0) < totalMinPt(0) Then totalMinPt(0) = bboxMin(0)
                            If bboxMin(1) < totalMinPt(1) Then totalMinPt(1) = bboxMin(1)
                            If bboxMax(0) > totalMaxPt(0) Then totalMaxPt(0) = bboxMax(0)
                            If bboxMax(1) > totalMaxPt(1) Then totalMaxPt(1) = bboxMax(1)
                        End If
                    End If
                    On Error GoTo 0
                Next i

                If firstEnt Then
                    MsgBox "Could not compute selection bounding box. Please select again.", vbExclamation
                    ss.Delete

                Else
                    centerPt(0) = (totalMinPt(0) + totalMaxPt(0)) / 2
                    centerPt(1) = (totalMinPt(1) + totalMaxPt(1)) / 2
                    centerPt(2) = 0

                    ' ----- 5. Scale all selected entities about the selection centre -----
                    scaleFactor = targetHeight / maxTextHeight
                    lastTargetHeight = targetHeight

                    doc.StartUndoMark

                    For i = 0 To ss.count - 1
                        Set ent = ss.item(i)
                        On Error Resume Next
                        ent.ScaleEntity centerPt, scaleFactor
                        On Error GoTo 0
                    Next i

                    doc.EndUndoMark

                    doc.Utility.prompt vbCr & _
                        "Done. " & ss.count & " object(s) scaled by " & Format(scaleFactor, "0.####") & _
                        "  (text height: " & Format(maxTextHeight, "0.##") & " mm  ?  " & _
                        Format(targetHeight, "0.##") & " mm)." & vbCr

                    ss.Delete
                End If
            End If
        End If
    Loop

Cleanup:
    ' Restore userform visibility
    If formWasVisible Then
        On Error Resume Next
        formPerfisul01.Show vbModeless
        On Error GoTo 0
    End If
End Sub

Attribute VB_Name = "M_sheetMetalWeight"
Option Explicit

' Calculate the total weight of sheet metal parts represented as region objects
' on the "Shapes" layer.
'
' Algorithm:
'   1. Collect all AcadRegion objects on the "Shapes" layer.
'   2. Compute the nesting depth of every region: how many other regions
'      fully contain it (determined via Boolean intersection copies).
'   3. Sum areas using the even-odd rule:
'        even depth (0, 2, …) ? add area  (outer material / island)
'        odd  depth (1, 3, …) ? subtract area (hole / cut)
'      Drawing units assumed to be mm, so areas are in mm².
'   4. Compute weight using values from formPerfisul01:
'        thickness  = valSheetThickness  (mm)
'        density    = valSheetDensity    (kg/m³)
'        weight (kg) = (totalArea_mm² / 1 000 000) × (thickness_mm / 1 000) × density_kg_m³
'   5. Insert a Text entity at (0, -40) with height 20 mm:
'        "Peso Total: XXX,XX kg"  (comma as decimal separator)

Public Sub CalculateSheetMetalWeight()
    On Error GoTo ErrHandler

    Dim doc As AcadDocument
    Set doc = ThisDrawing

    ' ------------------------------------------------------------------ '
    ' 1. Read parameters from the form
    ' ------------------------------------------------------------------ '
    Dim thicknessMm As Double
    Dim densityKgM3 As Double

    On Error Resume Next
    thicknessMm = CDbl(formPerfisul01.valSheetThickness.Value)
    If Err.Number <> 0 Then
        Err.Clear
        MsgBox "Não foi possível ler a espessura (valSheetThickness) do formulário.", _
               vbExclamation, "Peso da Chapa"
        Exit Sub
    End If
    densityKgM3 = CDbl(formPerfisul01.valSheetDensity.Value)
    If Err.Number <> 0 Then
        Err.Clear
        MsgBox "Não foi possível ler a densidade (valSheetDensity) do formulário.", _
               vbExclamation, "Peso da Chapa"
        Exit Sub
    End If
    On Error GoTo ErrHandler

    If thicknessMm <= 0 Then
        MsgBox "Espessura inválida: " & thicknessMm & " mm.", vbExclamation, "Peso da Chapa"
        Exit Sub
    End If
    If densityKgM3 <= 0 Then
        MsgBox "Densidade inválida: " & densityKgM3 & " kg/m³.", vbExclamation, "Peso da Chapa"
        Exit Sub
    End If

    ' ------------------------------------------------------------------ '
    ' 2. Collect all AcadRegion objects on layer "Shapes"
    ' ------------------------------------------------------------------ '
    Dim allRegs() As AcadRegion
    Dim regCount As Long
    regCount = 0
    ReDim allRegs(0 To doc.modelSpace.count - 1)

    Dim i As Long
    For i = 0 To doc.modelSpace.count - 1
        Dim ent As AcadEntity
        Set ent = doc.modelSpace.item(i)
        If UCase$(Trim$(ent.layer)) = "SHAPES" Then
            If TypeOf ent Is AcadRegion Then
                Set allRegs(regCount) = ent
                regCount = regCount + 1
            End If
        End If
    Next i

    If regCount = 0 Then
        MsgBox "Nenhuma região verde encontrada na camada ""Shapes"".", _
               vbExclamation, "Peso da Chapa"
        Exit Sub
    End If

    ReDim Preserve allRegs(0 To regCount - 1)

    ' ------------------------------------------------------------------ '
    ' 3. Compute nesting depth for each region (even-odd rule)
    '    nestDepth(i) = number of other regions that fully contain region i.
    '    Even depth ? material (add); Odd depth ? hole/cut (subtract).
    ' ------------------------------------------------------------------ '
    Dim j As Long
    Dim nestDepth() As Long
    ReDim nestDepth(0 To regCount - 1)
    For i = 0 To regCount - 1
        nestDepth(i) = 0
    Next i

    Dim copyA As AcadRegion
    Dim copyB As AcadRegion

    ' For each region i, count how many other regions j fully contain it.
    ' "Fully contained" means intersect(i, j) has the same area as i.
    ' Copies are used for the Boolean op so originals are never touched.
    For i = 0 To regCount - 1
        For j = 0 To regCount - 1
            If i <> j Then
                If allRegs(j).area >= allRegs(i).area Then
                    On Error Resume Next
                    Set copyA = allRegs(i).Copy
                    Set copyB = allRegs(j).Copy
                    Err.Clear
                    copyA.Boolean acIntersection, copyB

                    If Err.Number = 0 Then
                        If Abs(copyA.area - allRegs(i).area) < 0.0001 Then
                            nestDepth(i) = nestDepth(i) + 1
                        End If
                    End If

                    If Not copyA Is Nothing Then copyA.Delete
                    If Not copyB Is Nothing Then copyB.Delete
                    Err.Clear
                    On Error GoTo ErrHandler
                End If
            End If
        Next j
    Next i

    ' ------------------------------------------------------------------ '
    ' 4. Sum areas using even-odd rule: even depth ? add, odd ? subtract
    ' ------------------------------------------------------------------ '
    Dim totalAreaMm2 As Double
    totalAreaMm2 = 0
    For i = 0 To regCount - 1
        If (nestDepth(i) Mod 2) = 0 Then
            totalAreaMm2 = totalAreaMm2 + allRegs(i).area
        Else
            totalAreaMm2 = totalAreaMm2 - allRegs(i).area
        End If
    Next i

    ' ------------------------------------------------------------------ '
    ' 5. Calculate total weight
    '    weight (kg) = area (m²) × thickness (m) × density (kg/m³)
    '    area_m²     = totalAreaMm2 / 1 000 000
    '    thickness_m = thicknessMm  / 1 000
    ' ------------------------------------------------------------------ '
    Dim weightKg As Double
    weightKg = (totalAreaMm2 / 1000000#) * (thicknessMm / 1000#) * densityKgM3

    ' ------------------------------------------------------------------ '
    ' 6. Compute drawing-content bounding box to derive dynamic text metrics
    '    (considering only objects in layer "linha_grade")
    ' ------------------------------------------------------------------ '
    Dim bbMinX As Double, bbMinY As Double, bbMaxX As Double, bbMaxY As Double
    Dim bbFirst As Boolean: bbFirst = True
    Dim bbEnt As AcadEntity
    For Each bbEnt In doc.modelSpace
        If UCase$(Trim$(bbEnt.layer)) = "0" Or UCase$(Trim$(bbEnt.layer)) = "LINHA_GRADE" Then
            Dim bbMin As Variant, bbMax As Variant
            On Error Resume Next
            bbEnt.GetBoundingBox bbMin, bbMax
            If Err.Number = 0 Then
                If bbFirst Then
                    bbMinX = bbMin(0): bbMinY = bbMin(1)
                    bbMaxX = bbMax(0): bbMaxY = bbMax(1)
                    bbFirst = False
                Else
                    If bbMin(0) < bbMinX Then bbMinX = bbMin(0)
                    If bbMin(1) < bbMinY Then bbMinY = bbMin(1)
                    If bbMax(0) > bbMaxX Then bbMaxX = bbMax(0)
                    If bbMax(1) > bbMaxY Then bbMaxY = bbMax(1)
                End If
            End If
            Err.Clear
            On Error GoTo ErrHandler
        End If
    Next bbEnt

    Dim dx As Double, dy As Double
    If bbFirst Then
        ' Fallback: no entities found, use safe defaults
        dx = 1000
        dy = 1000
    Else
        dx = bbMaxX - bbMinX
        dy = bbMaxY - bbMinY
    End If

    ' ------------------------------------------------------------------ '
    ' 7. Insert result text using dynamic position and height
    '    textHeight = 0.015 * dY
    '    position   = ( 0.0035 * dY , 0.0035 * dY )
    ' ------------------------------------------------------------------ '
    ' Count outer (depth-0) regions = number of distinct parts
    Dim outerCount As Long
    outerCount = 0
    For i = 0 To regCount - 1
        If nestDepth(i) = 0 Then outerCount = outerCount + 1
    Next i

    ' Format with 2 decimal places, replacing "." with "," per Brazilian locale
    Dim weightStr As String
    weightStr = Format(weightKg, "0.00")
    weightStr = Replace(weightStr, ".", ",")

    Dim labelText As String
    labelText = "Qtd de peças: " & Format(outerCount, "00") & "   |   Peso Total: " & weightStr & " kg"

    Dim textHeight As Double
    textHeight = 0.01 * dy

    Dim insertPt(0 To 2) As Double
    insertPt(0) = 0.0065 * dy
    insertPt(1) = 0.0065 * dy
    insertPt(2) = 0

    doc.StartUndoMark

    ' Remove any previous weight label to avoid stacking on re-runs
    Dim existingEnt As AcadEntity
    For Each existingEnt In doc.modelSpace
        If TypeOf existingEnt Is AcadText Then
            On Error Resume Next
            Dim txtObj As AcadText
            Set txtObj = existingEnt
            If InStr(1, txtObj.TextString, "Quantidade de peças:", vbTextCompare) > 0 Or _
               InStr(1, txtObj.TextString, "Peso Total:", vbTextCompare) > 0 Then
                txtObj.Delete
            End If
            Err.Clear
            On Error GoTo ErrHandler
        End If
    Next existingEnt

    Dim newText As AcadText
    Set newText = doc.modelSpace.AddText(labelText, insertPt, textHeight)
    newText.layer = "0"
    newText.Color = acByLayer

    doc.EndUndoMark

    MsgBox "Peso calculado com sucesso!" & vbCr & vbCr & _
           "Quantidade de peças: " & outerCount & vbCr & _
           "Área líquida (externas - furos): " & Format(totalAreaMm2 / 1000000#, "#,##0.000000") & " m²" & vbCr & _
           "Espessura: " & thicknessMm & " mm" & vbCr & _
           "Densidade: " & densityKgM3 & " kg/m³" & vbCr & vbCr & _
           labelText, _
           vbInformation, "Peso da Chapa"

    Exit Sub

ErrHandler:
    MsgBox "Erro ao calcular peso: " & Err.Description, vbCritical, "Peso da Chapa"
    On Error Resume Next
    doc.EndUndoMark
End Sub

' ======================================================================== '
' ToggleShapeExclusion
' -----------------------------------------------------------------------  '
' Temporarily exclude (or re-include) individual regions from the weight
' calculation without touching their color.
'
' Mechanism:
'   - Active regions live on layer "Shapes"  (green)  ? counted by weight calc.
'   - Excluded regions live on layer "Shapes_Skip" (red) ? ignored by weight calc.
'
' Usage: run this sub, select one or more regions; each one is toggled
'   between the two layers. Run it again on the same region to restore it.
' ======================================================================== '
Public Sub ToggleShapeExclusion()
    On Error GoTo ErrHandler

    Dim doc As AcadDocument
    Set doc = ThisDrawing

    ' Hide the form so the user can interact freely with the drawing
    On Error Resume Next
    formPerfisul01.Hide
    On Error GoTo ErrHandler

    ' Ensure both layers exist before saving state (so they appear in the snapshot)
    EnsureShapesSkipLayer doc

    ' ------------------------------------------------------------------ '
    ' Save layer visibility state, then hide everything except the two
    ' Shapes layers so the user sees only what they need to select.
    ' ------------------------------------------------------------------ '
    Dim savedCount As Long
    savedCount = 0
    Dim savedNames() As String
    Dim savedOn() As Boolean
    ReDim savedNames(0 To doc.layers.count - 1)
    ReDim savedOn(0 To doc.layers.count - 1)

    Dim lyr As AcadLayer
    For Each lyr In doc.layers
        savedNames(savedCount) = lyr.name
        savedOn(savedCount) = lyr.LayerOn
        savedCount = savedCount + 1
        Dim layUp As String
        layUp = UCase$(Trim$(lyr.name))
        If layUp <> "SHAPES" And layUp <> "SHAPES_SKIP" Then
            On Error Resume Next
            lyr.LayerOn = False
            Err.Clear
            On Error GoTo ErrHandler
        Else
            On Error Resume Next
            lyr.LayerOn = True
            Err.Clear
            On Error GoTo ErrHandler
        End If
    Next lyr
    doc.Regen acAllViewports

    ' ------------------------------------------------------------------ '
    ' Build a selection set and let the user pick regions
    ' ------------------------------------------------------------------ '
    Dim ss As AcadSelectionSet
    On Error Resume Next
    Set ss = doc.SelectionSets.item("SMW_TOGGLE")
    If Err.Number = 0 Then ss.Delete
    Err.Clear
    On Error GoTo ErrHandler
    Set ss = doc.SelectionSets.Add("SMW_TOGGLE")

    doc.Utility.prompt vbCr & "Selecione regiões para (des)ativar no cálculo..." & vbCr
    ss.SelectOnScreen

    If ss.count = 0 Then
        MsgBox "Nenhum objeto selecionado.", vbExclamation, "Excluir/Incluir Forma"
        GoTo Cleanup
    End If

    doc.StartUndoMark

    Dim ent As AcadEntity
    Dim toggled As Long
    toggled = 0
    For Each ent In ss
        If Not TypeOf ent Is AcadRegion Then GoTo NextEnt
        Dim entLayer As String
        entLayer = UCase$(Trim$(ent.layer))
        Select Case entLayer
            Case "SHAPES"
                ent.layer = "Shapes_Skip"
            Case "SHAPES_SKIP"
                ent.layer = "Shapes"
            Case Else
                GoTo NextEnt   ' not a managed shape — skip silently
        End Select
        toggled = toggled + 1
NextEnt:
    Next ent

    doc.EndUndoMark

    If toggled = 0 Then
        MsgBox "Nenhuma região nas camadas ""Shapes"" ou ""Shapes_Skip"" foi selecionada.", _
               vbExclamation, "Excluir/Incluir Forma"
    Else
        MsgBox toggled & " região(ões) alternada(s) entre ""Shapes"" e ""Shapes_Skip""." & vbCr & vbCr & _
               "Regiões em ""Shapes_Skip"" (vermelho) serão ignoradas no cálculo de peso.", _
               vbInformation, "Excluir/Incluir Forma"
    End If

    GoTo Cleanup

ErrHandler:
    MsgBox "Erro ao alternar exclusão: " & Err.Description, vbCritical, "Excluir/Incluir Forma"
    On Error Resume Next
    doc.EndUndoMark
Cleanup:
    ' Restore every layer to its original visibility state
    On Error Resume Next
    Dim k As Long
    For k = 0 To savedCount - 1
        Dim lyrR As AcadLayer
        Set lyrR = doc.layers.item(savedNames(k))
        If Err.Number = 0 Then lyrR.LayerOn = savedOn(k)
        Err.Clear
    Next k
    ' Always leave Shapes / Shapes_Skip hidden after the tool exits
    Dim lyrHide As AcadLayer
    Set lyrHide = doc.layers.item("Shapes")
    If Err.Number = 0 Then lyrHide.LayerOn = False
    Err.Clear
    Set lyrHide = doc.layers.item("Shapes_Skip")
    If Err.Number = 0 Then lyrHide.LayerOn = False
    Err.Clear
    If savedCount > 0 Then doc.Regen acAllViewports

    ss.Delete

    ' Restore the form
    formPerfisul01.Show
    On Error GoTo 0
End Sub

Private Sub EnsureShapesSkipLayer(doc As AcadDocument)
    On Error Resume Next
    Dim lyr As AcadLayer
    Set lyr = doc.layers.item("Shapes_Skip")
    If Err.Number <> 0 Then
        Err.Clear
        Set lyr = doc.layers.Add("Shapes_Skip")
        lyr.Color = acRed          ' visually distinct from the green "Shapes" layer
    End If
    On Error GoTo 0
End Sub

Attribute VB_Name = "M_textRotateToLine"
Option Explicit

Public Sub RotateTextToLineAngle()
    On Error GoTo ErrorHandler
    
    Dim acadApp As AcadApplication
    Dim acadDoc As AcadDocument
    Dim objLine As Object ' AcadLine
    Dim objText As Object ' AcadText or AcadMText
    Dim pickPt As Variant
    Dim lineAngle As Double
    Dim midPt As Variant
    
    Set acadApp = ThisDrawing.Application
    Set acadDoc = ThisDrawing
    
    Do While True
        ' Select the line
        Err.Clear
        On Error Resume Next
        acadDoc.Utility.GetEntity objLine, pickPt, vbCrLf & "Select a line (<Esc> to stop): "
        If Err.Number <> 0 Then Exit Do ' Esc cancels the loop
        On Error GoTo ErrorHandler
        
        If objLine.ObjectName <> "AcDbLine" Then
            MsgBox "Please select a line entity.", vbExclamation
            GoTo ContinueLoop
        End If
        midPt = midPoint(objLine.startPoint, objLine.endPoint)
        
        ' Apply scale factor of -1 to invert the line's direction
        objLine.ScaleEntity midPt, -1
        
        ' Select the text (Text or MText)
        Err.Clear
        On Error Resume Next
        acadDoc.Utility.GetEntity objText, pickPt, vbCrLf & "Select a text (TEXT/MTEXT) (<Esc> to stop): "
        If Err.Number <> 0 Then Exit Do ' Esc cancels the loop
        On Error GoTo ErrorHandler
        
        If Not (objText.ObjectName = "AcDbText" Or objText.ObjectName = "AcDbMText") Then
            MsgBox "Please select a TEXT or MTEXT entity.", vbExclamation
            GoTo ContinueLoop
        End If
        
        lineAngle = objLine.angle ' radians
        objText.rotation = lineAngle

        ' Place text at line midpoint and align bottom-center
        If objText.ObjectName = "AcDbText" Then
            objText.Alignment = acAlignmentBottomCenter
            objText.TextAlignmentPoint = midPt
            objText.InsertionPoint = midPt
        ElseIf objText.ObjectName = "AcDbMText" Then
            objText.AttachmentPoint = acAttachmentPointBottomCenter
            objText.InsertionPoint = midPt
        End If
        
        acadDoc.Regen acAllViewports
ContinueLoop:
    Loop
    Exit Sub
    
ErrorHandler:
    MsgBox "Error: " & Err.Description, vbCritical
End Sub

Private Function midPoint(p1 As Variant, p2 As Variant) As Variant
    Dim m(0 To 2) As Double
    m(0) = (p1(0) + p2(0)) / 2
    m(1) = (p1(1) + p2(1)) / 2
    m(2) = (p1(2) + p2(2)) / 2
    midPoint = m
End Function

Attribute VB_Name = "M_totalPerimeter"

' Helper to copy text to clipboard using Windows API (no MSForms required)
Private Declare PtrSafe Function OpenClipboard Lib "user32" (ByVal hWnd As LongPtr) As Long
Private Declare PtrSafe Function CloseClipboard Lib "user32" () As Long
Private Declare PtrSafe Function EmptyClipboard Lib "user32" () As Long
Private Declare PtrSafe Function SetClipboardData Lib "user32" (ByVal wFormat As Long, ByVal hMem As LongPtr) As LongPtr
Private Declare PtrSafe Function GlobalAlloc Lib "kernel32" (ByVal wFlags As Long, ByVal dwBytes As LongPtr) As LongPtr
Private Declare PtrSafe Function GlobalLock Lib "kernel32" (ByVal hMem As LongPtr) As LongPtr
Private Declare PtrSafe Function GlobalUnlock Lib "kernel32" (ByVal hMem As LongPtr) As Long
Private Declare PtrSafe Function GlobalFree Lib "kernel32" (ByVal hMem As LongPtr) As LongPtr
Private Declare PtrSafe Sub CopyMemory Lib "kernel32" Alias "RtlMoveMemory" (ByVal Destination As LongPtr, ByVal Source As LongPtr, ByVal Length As LongPtr)

Private Const CF_TEXT As Long = 1
Private Const GMEM_MOVEABLE As Long = &H2


Public Sub SumTotalPerimeter()
    Dim doc As AcadDocument
    Dim ent As AcadEntity
    Dim totalPerimeter As Double
    Dim strResult As String
    Dim layerName As String
    Dim i As Long

    Set doc = ThisDrawing

    ' Get layer name from combobox cbCamada02
    On Error Resume Next
    layerName = formPerfisul01.cbCamada02.Value
    On Error GoTo 0
    If layerName = "" Then
        MsgBox "No layer selected in cbCamada02. Operation cancelled.", vbExclamation
        Exit Sub
    End If

    totalPerimeter = 0

    ' Loop through all entities in ModelSpace
    For i = 0 To doc.modelSpace.count - 1
        Set ent = doc.modelSpace.item(i)
        If UCase(ent.layer) = UCase(layerName) Then
            On Error Resume Next
            Select Case ent.ObjectName
                Case "AcDbLine"
                    totalPerimeter = totalPerimeter + ent.Length
                Case "AcDbPolyline", "AcDb2dPolyline", "AcDb3dPolyline"
                    totalPerimeter = totalPerimeter + ent.Length
                Case "AcDbCircle"
                    totalPerimeter = totalPerimeter + ent.Circumference
                Case "AcDbArc"
                    totalPerimeter = totalPerimeter + ent.ArcLength
                Case "AcDbEllipse"
                    totalPerimeter = totalPerimeter + ent.ArcLength
                Case "AcDbSpline"
                    ' Calculate spline length by sampling points along the curve
                    Dim spline As AcadSpline
                    Dim splineLen As Double
                    Dim pt1 As Variant, pt2 As Variant
                    Dim numSamples As Integer
                    Dim j As Integer
                    Dim t As Double, tStart As Double, tEnd As Double
                    
                    Set spline = ent
                    splineLen = 0
                    numSamples = 100
                    
                    ' Get start and end fit points to estimate parameter range
                    Dim fitPts As Variant
                    Dim ctrlPts As Variant
                    ctrlPts = spline.ControlPoints
                    
                    ' Approximate length by summing distances between sampled points
                    tStart = 0
                    tEnd = 1
                    
                    On Error Resume Next
                    pt1 = spline.GetPointAtParam(tStart)
                    If Err.Number <> 0 Then
                        ' Try using control points to approximate
                        Err.Clear
                        Dim k As Integer
                        For k = 0 To (UBound(ctrlPts) - 3) Step 3
                            splineLen = splineLen + Sqr((ctrlPts(k + 3) - ctrlPts(k)) ^ 2 + _
                                                        (ctrlPts(k + 4) - ctrlPts(k + 1)) ^ 2 + _
                                                        (ctrlPts(k + 5) - ctrlPts(k + 2)) ^ 2)
                        Next k
                    Else
                        ' Sample points along parameter range
                        For j = 1 To numSamples
                            t = tStart + (tEnd - tStart) * (j / numSamples)
                            pt2 = spline.GetPointAtParam(t)
                            If Err.Number = 0 Then
                                splineLen = splineLen + Sqr((pt2(0) - pt1(0)) ^ 2 + _
                                                            (pt2(1) - pt1(1)) ^ 2 + _
                                                            (pt2(2) - pt1(2)) ^ 2)
                                pt1 = pt2
                            End If
                        Next j
                    End If
                    On Error Resume Next
                    
                    totalPerimeter = totalPerimeter + splineLen
                ' Add more cases as needed for other entity types
            End Select
            On Error GoTo 0
        End If
    Next i

    strResult = "Total Perimeter on layer '" & layerName & "': " & Format(totalPerimeter, "0.00")
    MsgBox strResult, vbInformation, "Sum of Perimeters"

    ' Copy to clipboard
    CopyTextToClipboard Format(totalPerimeter, "0.00")
End Sub


Public Sub CopyTextToClipboard(ByVal sText As String)
    Dim hGlobalMemory As LongPtr
    Dim lpGlobalMemory As LongPtr
    Dim hWnd As LongPtr
    Dim sData As String
    Dim lSize As Long

    sData = sText & vbNullChar
    lSize = LenB(sData)

    hGlobalMemory = GlobalAlloc(GMEM_MOVEABLE, lSize)
    If hGlobalMemory Then
        lpGlobalMemory = GlobalLock(hGlobalMemory)
        If lpGlobalMemory Then
            CopyMemory lpGlobalMemory, StrPtr(sData), lSize
            GlobalUnlock hGlobalMemory
            If OpenClipboard(0&) Then
                EmptyClipboard
                SetClipboardData CF_TEXT, hGlobalMemory
                CloseClipboard
            End If
        End If
    End If
End Sub

Attribute VB_Name = "Module_rotateAndCircle"
Option Explicit

Public Sub RotateLinesAndCreateCircle()
    On Error GoTo ErrorHandler
    
    Dim acadApp As AcadApplication
    Dim acadDoc As AcadDocument
    Dim lineA As Object ' AcadLine
    Dim lineB As Object ' AcadLine
    Dim objEntity As Object ' AcadEntity
    Dim lineR1 As Object ' AcadLine
    Dim lineR2 As Object ' AcadLine
    Dim commonPoint As Variant
    Dim foundCommonPoint As Boolean
    Dim TOLERANCE As Double
    Dim layer0 As AcadLayer
    Dim lineA1 As Object ' AcadLine
    Dim lineA2 As Object ' AcadLine
    Dim lineB1 As Object ' AcadLine
    Dim lineB2 As Object ' AcadLine
    Dim angle90 As Double
    Dim angleMinus90 As Double
    Dim objCircle As Object ' AcadCircle
    Dim radius As Double
    
    ' Get the active document
    Set acadApp = ThisDrawing.Application
    Set acadDoc = ThisDrawing
    
    ' Set tolerance for point comparison (small value for coordinate matching)
    TOLERANCE = 0.0001

    Do While True
        ' Prompt user to select first line (Line A)
        Err.Clear
        On Error Resume Next
        acadDoc.Utility.GetEntity objEntity, commonPoint, vbCrLf & "Select Line A (<Esc> to stop): "
        If Err.Number <> 0 Then Exit Do ' Esc cancels the loop
        On Error GoTo ErrorHandler
        
        ' Check if selected entity is a line
        If objEntity.ObjectName <> "AcDbLine" Then
            MsgBox "Selected entity is not a line. Please select a line.", vbExclamation
            GoTo ContinueLoop
        End If
        Set lineA = objEntity
        
        ' Prompt user to select second line (Line B)
        Err.Clear
        On Error Resume Next
        acadDoc.Utility.GetEntity objEntity, commonPoint, vbCrLf & "Select Line B (<Esc> to stop): "
        If Err.Number <> 0 Then Exit Do ' Esc cancels the loop
        On Error GoTo ErrorHandler
        
        ' Check if selected entity is a line
        If objEntity.ObjectName <> "AcDbLine" Then
            MsgBox "Selected entity is not a line. Please select a line.", vbExclamation
            GoTo ContinueLoop
        End If
        Set lineB = objEntity
        
        ' Find common endpoint (Point C)
        foundCommonPoint = False
        
        ' Check if Line A's start point matches Line B's start point
        If PointsAreEqual(lineA.startPoint, lineB.startPoint, TOLERANCE) Then
            commonPoint = lineA.startPoint
            foundCommonPoint = True
        ' Check if Line A's start point matches Line B's end point
        ElseIf PointsAreEqual(lineA.startPoint, lineB.endPoint, TOLERANCE) Then
            commonPoint = lineA.startPoint
            foundCommonPoint = True
        ' Check if Line A's end point matches Line B's start point
        ElseIf PointsAreEqual(lineA.endPoint, lineB.startPoint, TOLERANCE) Then
            commonPoint = lineA.endPoint
            foundCommonPoint = True
        ' Check if Line A's end point matches Line B's end point
        ElseIf PointsAreEqual(lineA.endPoint, lineB.endPoint, TOLERANCE) Then
            commonPoint = lineA.endPoint
            foundCommonPoint = True
        End If
        
        ' If no common point found, skip this iteration
        If Not foundCommonPoint Then
            MsgBox "The selected lines do not share a common endpoint.", vbExclamation
            GoTo ContinueLoop
        End If
        
        ' Ensure Layer 0 exists (it should always exist)
        On Error Resume Next
        Set layer0 = acadDoc.layers.item("0")
        On Error GoTo ErrorHandler
        
        ' Create the four rotated lines
        
        ' Define rotation angles (in radians)
        angle90 = 90 * 3.14159265358979 / 180      ' 90 degrees
        angleMinus90 = -90 * 3.14159265358979 / 180 ' -90 degrees
        
        ' Copy and rotate Line A by +90 degrees (Line A1)
        Set lineA1 = lineA.Copy
        lineA1.layer = "0"
        Call RotateLineAroundPoint(lineA1, commonPoint, angle90)
        Call EnsureStartsAtPoint(lineA1, commonPoint, TOLERANCE)
        
        ' Copy and rotate Line A by -90 degrees (Line A2)
        Set lineA2 = lineA.Copy
        lineA2.layer = "0"
        Call RotateLineAroundPoint(lineA2, commonPoint, angleMinus90)
        Call EnsureStartsAtPoint(lineA2, commonPoint, TOLERANCE)
        
        ' Copy and rotate Line B by +90 degrees (Line B1)
        Set lineB1 = lineB.Copy
        lineB1.layer = "0"
        Call RotateLineAroundPoint(lineB1, commonPoint, angle90)
        Call EnsureStartsAtPoint(lineB1, commonPoint, TOLERANCE)
        
        ' Copy and rotate Line B by -90 degrees (Line B2)
        Set lineB2 = lineB.Copy
        lineB2.layer = "0"
        Call RotateLineAroundPoint(lineB2, commonPoint, angleMinus90)
        Call EnsureStartsAtPoint(lineB2, commonPoint, TOLERANCE)

        ' Add center lines in red using angle bisectors between rotated pairs
        Dim midStart1 As Variant
        Dim midEnd1 As Variant
        Dim midStart2 As Variant
        Dim midEnd2 As Variant
        Dim lenR1 As Double
        Dim lenR2 As Double
        Dim dirR1 As Variant
        Dim dirR2 As Variant
        Dim newEndR1 As Variant
        Dim newEndR2 As Variant

        midStart1 = midPoint(lineA1.startPoint, lineB2.startPoint)
        midEnd1 = midPoint(lineA1.endPoint, lineB2.endPoint)
        midStart2 = midPoint(lineA2.startPoint, lineB1.startPoint)
        midEnd2 = midPoint(lineA2.endPoint, lineB1.endPoint)

        lenR1 = DistanceBetweenPoints(midStart1, midEnd1)
        lenR2 = DistanceBetweenPoints(midStart2, midEnd2)

        dirR1 = BisectorDirection(lineA1, lineB2, TOLERANCE)
        dirR2 = BisectorDirection(lineA2, lineB1, TOLERANCE)

        newEndR1 = PointAlongDirection(midStart1, dirR1, lenR1)
        newEndR2 = PointAlongDirection(midStart2, dirR2, lenR2)

        Set lineR1 = acadDoc.modelSpace.AddLine(midStart1, newEndR1)
        lineR1.layer = "0"
        lineR1.Color = 1 ' red

        Set lineR2 = acadDoc.modelSpace.AddLine(midStart2, newEndR2)
        lineR2.layer = "0"
        lineR2.Color = 1 ' red
        
        ' Create objCircle at Point C with 1.3mm radius
        radius = 1.3 ' 1.3mm radius
        
        Set objCircle = acadDoc.modelSpace.AddCircle(commonPoint, radius)
        objCircle.layer = "0"
        
        ' Refresh the display
        acadDoc.Regen acAllViewports
ContinueLoop:
    Loop
    
       '  MsgBox "Operation completed successfully!" & vbCrLf & "Created 4 rotated lines and 1 objCircle at the common endpoint.", vbInformation
    
        Exit Sub

ErrorHandler:
    MsgBox "Error: " & Err.Description, vbCritical
End Sub

' Helper function to check if two points are equal within tolerance
Private Function PointsAreEqual(point1 As Variant, point2 As Variant, TOLERANCE As Double) As Boolean
    Dim dx As Double, dy As Double, dz As Double
    
    dx = Abs(point1(0) - point2(0))
    dy = Abs(point1(1) - point2(1))
    dz = Abs(point1(2) - point2(2))
    
    If dx < TOLERANCE And dy < TOLERANCE And dz < TOLERANCE Then
        PointsAreEqual = True
    Else
        PointsAreEqual = False
    End If
End Function

' Helper subroutine to rotate a line around a point
Private Sub RotateLineAroundPoint(line As AcadLine, basePoint As Variant, angle As Double)
    Dim newStartPoint As Variant
    Dim newEndPoint As Variant
    
    ' Rotate start point
    newStartPoint = RotatePointAroundBase(line.startPoint, basePoint, angle)
    
    ' Rotate end point
    newEndPoint = RotatePointAroundBase(line.endPoint, basePoint, angle)
    
    ' Update line coordinates
    line.startPoint = newStartPoint
    line.endPoint = newEndPoint
End Sub

' Helper function to rotate a point around a base point
Private Function RotatePointAroundBase(point As Variant, basePoint As Variant, angle As Double) As Variant
    Dim dx As Double, dy As Double
    Dim newX As Double, newY As Double
    Dim cosAngle As Double, sinAngle As Double
    Dim result(0 To 2) As Double
    
    ' Calculate relative position from base point
    dx = point(0) - basePoint(0)
    dy = point(1) - basePoint(1)
    
    ' Calculate cos and sin of rotation angle
    cosAngle = Cos(angle)
    sinAngle = Sin(angle)
    
    ' Apply rotation matrix
    newX = dx * cosAngle - dy * sinAngle
    newY = dx * sinAngle + dy * cosAngle
    
    ' Translate back to original coordinate system
    result(0) = basePoint(0) + newX
    result(1) = basePoint(1) + newY
    result(2) = point(2) ' Keep Z coordinate unchanged
    
    RotatePointAroundBase = result
End Function

Private Function midPoint(p1 As Variant, p2 As Variant) As Variant
    Dim m(0 To 2) As Double
    m(0) = (p1(0) + p2(0)) / 2
    m(1) = (p1(1) + p2(1)) / 2
    m(2) = (p1(2) + p2(2)) / 2
    midPoint = m
End Function

Private Sub EnsureStartsAtPoint(ln As Object, targetPoint As Variant, tol As Double)
    ' Ensure the line's StartPoint is the target; if not, swap start/end
    If Not PointsAreEqual(ln.startPoint, targetPoint, tol) Then
        Dim tmpStart As Variant
        tmpStart = ln.startPoint
        ln.startPoint = ln.endPoint
        ln.endPoint = tmpStart
    End If
End Sub

Private Function DistanceBetweenPoints(p1 As Variant, p2 As Variant) As Double
    Dim dx As Double, dy As Double, dz As Double
    dx = p1(0) - p2(0)
    dy = p1(1) - p2(1)
    dz = p1(2) - p2(2)
    DistanceBetweenPoints = Sqr(dx * dx + dy * dy + dz * dz)
End Function

Private Function VectorFromPoints(p1 As Variant, p2 As Variant) As Variant
    Dim v(0 To 2) As Double
    v(0) = p2(0) - p1(0)
    v(1) = p2(1) - p1(1)
    v(2) = p2(2) - p1(2)
    VectorFromPoints = v
End Function

Private Function VectorLength(v As Variant) As Double
    VectorLength = Sqr(v(0) * v(0) + v(1) * v(1) + v(2) * v(2))
End Function

Private Function NormalizeVector(v As Variant) As Variant
    Dim dLen As Double
    Dim n(0 To 2) As Double
    dLen = VectorLength(v)
    If dLen = 0 Then
        n(0) = 0: n(1) = 0: n(2) = 0
    Else
        n(0) = v(0) / dLen
        n(1) = v(1) / dLen
        n(2) = v(2) / dLen
    End If
    NormalizeVector = n
End Function

Private Function AddVectors(v1 As Variant, v2 As Variant) As Variant
    Dim r(0 To 2) As Double
    r(0) = v1(0) + v2(0)
    r(1) = v1(1) + v2(1)
    r(2) = v1(2) + v2(2)
    AddVectors = r
End Function

Private Function ScaleVector(v As Variant, factor As Double) As Variant
    Dim r(0 To 2) As Double
    r(0) = v(0) * factor
    r(1) = v(1) * factor
    r(2) = v(2) * factor
    ScaleVector = r
End Function

Private Function PointAlongDirection(basePoint As Variant, dirUnit As Variant, dist As Double) As Variant
    Dim r(0 To 2) As Double
    r(0) = basePoint(0) + dirUnit(0) * dist
    r(1) = basePoint(1) + dirUnit(1) * dist
    r(2) = basePoint(2) + dirUnit(2) * dist
    PointAlongDirection = r
End Function

Private Function LineDirectionUnit(ln As Object) As Variant
    LineDirectionUnit = NormalizeVector(VectorFromPoints(ln.startPoint, ln.endPoint))
End Function

Private Function BisectorDirection(ln1 As Object, ln2 As Object, tol As Double) As Variant
    Dim u1 As Variant
    Dim u2 As Variant
    Dim sumVec As Variant

    u1 = LineDirectionUnit(ln1)
    u2 = LineDirectionUnit(ln2)
    sumVec = AddVectors(u1, u2)

    If VectorLength(sumVec) < tol Then
        BisectorDirection = u1 ' fallback when directions oppose each other
    Else
        BisectorDirection = NormalizeVector(sumVec)
    End If
End Function

Attribute VB_Name = "Module_simplifyContours"
Option Explicit

' Converts a selected chain of lines, polylines and/or arcs into a spline,
' deleting the original entities. Runs in a loop until the user presses ESC
' or cancels the selection.

' Number of intermediate points used to sample each arc segment
Private Const ARC_SAMPLE_STEPS As Long = 16

' Snap tolerance for chain detection (drawing units)
Private Const CHAIN_TOL As Double = 0.01

Private Type Point2D
    X As Double
    Y As Double
End Type

' Represents a segment extracted from any entity type (line, arc, polyline).
' StartPt / EndPt are the physical endpoints; Points holds the full sampled
' point sequence from StartPt to EndPt.
Private Type Segment
    StartPt  As Point2D
    EndPt    As Point2D
    PtCount  As Long          ' number of entries in Pts()
    pts(0 To 512) As Point2D  ' sampled interior + endpoints
    entIdx   As Long          ' index in the original ss for deletion
End Type

Public Sub SimplifySelectedContours()
    Dim doc As Object
    Set doc = ThisDrawing

    Dim wasFormVisible As Boolean
    On Error Resume Next
    wasFormVisible = formPerfisul01.Visible
    If wasFormVisible Then formPerfisul01.Hide
    On Error GoTo SafeExit

    doc.Utility.prompt "Chain-to-Spline: area-select a chain of lines/polylines/arcs, then press ENTER. Press ESC to exit." & vbCrLf

    Dim ss As Object
    Set ss = PrepareSelectionSet(doc, "SIMP_CHAIN")
    If ss Is Nothing Then Exit Sub

    Do
        ss.Clear

        doc.Utility.prompt "Select chain (window/crossing) then ENTER, or ESC to exit: "

        On Error Resume Next
        ss.SelectOnScreen
        Dim selErr As Long: selErr = Err.Number
        On Error GoTo 0

        If selErr <> 0 Or ss.count = 0 Then
            doc.Utility.prompt "Exit." & vbCrLf
            Exit Do
        End If

        Dim converted As Long
        converted = ConvertChainToSpline(doc, ss)

        If converted = 0 Then
            doc.Utility.prompt "No connected chain found in selection." & vbCrLf
        Else
            doc.Utility.prompt converted & " spline(s) drawn." & vbCrLf
        End If
    Loop

SafeExit:
    On Error Resume Next
    If wasFormVisible Then formPerfisul01.Show
    On Error GoTo 0
End Sub

' ---------------------------------------------------------------------------
' Chain detection and spline conversion
' ---------------------------------------------------------------------------

' Convert selection to chains and draw one spline per chain.
Private Function ConvertChainToSpline(ByVal doc As Object, _
                                      ByVal ss As Object) As Long
    ' 1. Collect segments from all supported entities
    Dim segs() As Segment
    Dim segCount As Long
    ReDim segs(0 To ss.count - 1)  ' upper bound; may not all be used

    Dim i As Long
    For i = 0 To ss.count - 1
        Dim ent As Object
        Set ent = ss.item(i)
        If ExtractSegment(ent, i, segs(segCount)) Then
            segCount = segCount + 1
        End If
    Next i

    If segCount = 0 Then Exit Function

    ' 2. Chain segments into ordered paths
    Dim used() As Boolean
    ReDim used(0 To segCount - 1)

    Dim splineCount As Long

    Dim s As Long
    For s = 0 To segCount - 1
        If used(s) Then GoTo NextSeg

        ' Start a new chain from this segment
        Dim chain() As Point2D
        Dim chainLen As Long
        Dim usedInChain() As Long
        ReDim usedInChain(0 To segCount - 1)
        Dim usedInChainCount As Long

        chain = CopySegPoints(segs(s))
        chainLen = segs(s).PtCount
        used(s) = True
        usedInChain(0) = s
        usedInChainCount = 1

        ' Grow chain by connecting matching endpoints
        Dim extended As Boolean
        Do
            extended = False
            Dim j As Long
            For j = 0 To segCount - 1
                If used(j) Then GoTo NextSegJ

                ' Try attaching segment j to either end of the chain
                If PointsAreEqual(chain(chainLen - 1), segs(j).StartPt, CHAIN_TOL) Then
                    ' Append seg j forward (skip duplicate junction point)
                    chain = AppendSegPoints(chain, chainLen, segs(j), True)
                    chainLen = chainLen + segs(j).PtCount - 1
                    used(j) = True
                    usedInChain(usedInChainCount) = j
                    usedInChainCount = usedInChainCount + 1
                    extended = True
                    GoTo RestartChain
                ElseIf PointsAreEqual(chain(chainLen - 1), segs(j).EndPt, CHAIN_TOL) Then
                    ' Append seg j reversed
                    chain = AppendSegPointsRev(chain, chainLen, segs(j), True)
                    chainLen = chainLen + segs(j).PtCount - 1
                    used(j) = True
                    usedInChain(usedInChainCount) = j
                    usedInChainCount = usedInChainCount + 1
                    extended = True
                    GoTo RestartChain
                ElseIf PointsAreEqual(chain(0), segs(j).EndPt, CHAIN_TOL) Then
                    ' Prepend seg j forward (its end connects to chain start)
                    chain = PrependSegPoints(chain, chainLen, segs(j), True)
                    chainLen = chainLen + segs(j).PtCount - 1
                    used(j) = True
                    usedInChain(usedInChainCount) = j
                    usedInChainCount = usedInChainCount + 1
                    extended = True
                    GoTo RestartChain
                ElseIf PointsAreEqual(chain(0), segs(j).StartPt, CHAIN_TOL) Then
                    ' Prepend seg j reversed
                    chain = PrependSegPointsRev(chain, chainLen, segs(j), True)
                    chainLen = chainLen + segs(j).PtCount - 1
                    used(j) = True
                    usedInChain(usedInChainCount) = j
                    usedInChainCount = usedInChainCount + 1
                    extended = True
                    GoTo RestartChain
                End If
NextSegJ:
            Next j
RestartChain:
        Loop While extended

        ' Need at least 2 distinct points for a spline
        If chainLen < 2 Then GoTo NextSeg

        ' Remove duplicate points from chain
        Dim cleanChain() As Point2D
        Dim cleanLen As Long
        CleanDuplicates chain, chainLen, cleanChain, cleanLen

        If cleanLen < 2 Then GoTo NextSeg

        ' 3. Draw spline through chain points
        Dim splineCoords() As Double
        ReDim splineCoords(0 To cleanLen * 3 - 1)
        Dim k As Long
        For k = 0 To cleanLen - 1
            splineCoords(k * 3) = cleanChain(k).X
            splineCoords(k * 3 + 1) = cleanChain(k).Y
            splineCoords(k * 3 + 2) = 0#
        Next k

        Dim startTan(0 To 2) As Double
        Dim endTan(0 To 2) As Double

        ' Tangents at endpoints: direction of first/last segment
        startTan(0) = cleanChain(1).X - cleanChain(0).X
        startTan(1) = cleanChain(1).Y - cleanChain(0).Y
        startTan(2) = 0#
        endTan(0) = cleanChain(cleanLen - 1).X - cleanChain(cleanLen - 2).X
        endTan(1) = cleanChain(cleanLen - 1).Y - cleanChain(cleanLen - 2).Y
        endTan(2) = 0#

        On Error Resume Next
        Dim spl As Object
        Set spl = doc.modelSpace.AddSpline(splineCoords, startTan, endTan)
        If Err.Number <> 0 Then
            Err.Clear
            On Error GoTo 0
            GoTo NextSeg
        End If
        On Error GoTo 0

        spl.Update
        splineCount = splineCount + 1

        ' 4. Delete original entities that were chained
        Dim d As Long
        For d = 0 To usedInChainCount - 1
            Dim entIdx As Long
            entIdx = segs(usedInChain(d)).entIdx
            On Error Resume Next
            ss.item(entIdx).Delete
            On Error GoTo 0
        Next d

NextSeg:
    Next s

    ConvertChainToSpline = splineCount
End Function

' ---- Segment extraction ----------------------------------------------------

Private Function ExtractSegment(ByVal ent As Object, ByVal ssIdx As Long, _
                                ByRef seg As Segment) As Boolean
    Dim t As String
    t = TypeName(ent)

    Select Case t
        Case "IAcadLine", "AcadLine"
            seg.StartPt = ToPoint2D(ent.startPoint)
            seg.EndPt = ToPoint2D(ent.endPoint)
            seg.PtCount = 2
            seg.pts(0) = seg.StartPt
            seg.pts(1) = seg.EndPt
            seg.entIdx = ssIdx
            ExtractSegment = True

        Case "IAcadArc", "AcadArc"
            ExtractSegment = SampleArc(ent, ssIdx, seg)

        Case "IAcadLWPolyline", "AcadLWPolyline"
            ExtractSegment = SampleLWPolyline(ent, ssIdx, seg)

        Case "IAcadPolyline", "AcadPolyline"
            ExtractSegment = Sample3DPolyline(ent, ssIdx, seg)

        Case Else
            ExtractSegment = False
    End Select
End Function

Private Function SampleArc(ByVal arc As Object, ByVal ssIdx As Long, _
                            ByRef seg As Segment) As Boolean
    Dim startAng As Double: startAng = arc.startAngle
    Dim endAng   As Double: endAng = arc.endAngle
    Dim cx As Double:       cx = arc.center(0)
    Dim cy As Double:       cy = arc.center(1)
    Dim r  As Double:       r = arc.radius

    ' Normalise so we sweep CCW from startAng to endAng
    Dim span As Double
    span = endAng - startAng
    If span <= 0# Then span = span + 2# * 3.14159265358979

    Dim steps As Long: steps = ARC_SAMPLE_STEPS
    Dim n As Long:     n = steps + 1          ' number of points
    If n > 512 Then n = 512

    Dim i As Long
    For i = 0 To n - 1
        Dim ang As Double
        ang = startAng + span * i / (n - 1)
        seg.pts(i).X = cx + r * Cos(ang)
        seg.pts(i).Y = cy + r * Sin(ang)
    Next i

    seg.PtCount = n
    seg.StartPt = seg.pts(0)
    seg.EndPt = seg.pts(n - 1)
    seg.entIdx = ssIdx
    SampleArc = True
End Function

Private Function SampleLWPolyline(ByVal pl As Object, ByVal ssIdx As Long, _
                                  ByRef seg As Segment) As Boolean
    Dim arr As Variant: arr = pl.Coordinates
    Dim total As Long:  total = (UBound(arr) + 1) \ 2
    If total < 2 Then Exit Function
    If total > 513 Then total = 513

    Dim i As Long
    For i = 0 To total - 1
        seg.pts(i).X = arr(2 * i)
        seg.pts(i).Y = arr(2 * i + 1)
    Next i

    seg.PtCount = total
    seg.StartPt = seg.pts(0)
    seg.EndPt = seg.pts(total - 1)
    seg.entIdx = ssIdx
    SampleLWPolyline = True
End Function

Private Function Sample3DPolyline(ByVal pl As Object, ByVal ssIdx As Long, _
                                  ByRef seg As Segment) As Boolean
    Dim arr As Variant: arr = pl.Coordinates
    Dim total As Long:  total = (UBound(arr) + 1) \ 3
    If total < 2 Then Exit Function
    If total > 513 Then total = 513

    Dim i As Long
    For i = 0 To total - 1
        seg.pts(i).X = arr(3 * i)
        seg.pts(i).Y = arr(3 * i + 1)
    Next i

    seg.PtCount = total
    seg.StartPt = seg.pts(0)
    seg.EndPt = seg.pts(total - 1)
    seg.entIdx = ssIdx
    Sample3DPolyline = True
End Function

' ---- Chain point helpers ----------------------------------------------------

Private Function CopySegPoints(ByRef seg As Segment) As Point2D()
    Dim out() As Point2D
    ReDim out(0 To seg.PtCount - 1)
    Dim i As Long
    For i = 0 To seg.PtCount - 1
        out(i) = seg.pts(i)
    Next i
    CopySegPoints = out
End Function

' Append seg points to existing chain (skip first point if skipFirst = True to
' avoid duplicating the junction).
Private Function AppendSegPoints(ByRef chain() As Point2D, ByVal chainLen As Long, _
                                 ByRef seg As Segment, ByVal skipFirst As Boolean) As Point2D()
    Dim startI As Long: startI = IIf(skipFirst, 1, 0)
    Dim addCount As Long: addCount = seg.PtCount - startI
    Dim newLen As Long: newLen = chainLen + addCount
    ReDim Preserve chain(0 To newLen - 1)
    Dim i As Long
    For i = 0 To addCount - 1
        chain(chainLen + i) = seg.pts(startI + i)
    Next i
    AppendSegPoints = chain
End Function

Private Function AppendSegPointsRev(ByRef chain() As Point2D, ByVal chainLen As Long, _
                                    ByRef seg As Segment, ByVal skipFirst As Boolean) As Point2D()
    ' Append seg in reverse order (seg.EndPt first, seg.StartPt last)
    ' skipFirst: skip seg.EndPt (the junction already in chain)
    Dim startI As Long: startI = IIf(skipFirst, seg.PtCount - 2, seg.PtCount - 1)
    Dim addCount As Long: addCount = startI + 1
    Dim newLen As Long: newLen = chainLen + addCount
    ReDim Preserve chain(0 To newLen - 1)
    Dim i As Long
    For i = 0 To addCount - 1
        chain(chainLen + i) = seg.pts(startI - i)
    Next i
    AppendSegPointsRev = chain
End Function

Private Function PrependSegPoints(ByRef chain() As Point2D, ByVal chainLen As Long, _
                                  ByRef seg As Segment, ByVal skipFirst As Boolean) As Point2D()
    ' Prepend seg (forward) before chain; seg.EndPt connects to chain(0)
    ' skipFirst: skip seg.EndPt
    Dim endI As Long: endI = IIf(skipFirst, seg.PtCount - 2, seg.PtCount - 1)
    Dim addCount As Long: addCount = endI + 1
    Dim newLen As Long: newLen = chainLen + addCount
    Dim out() As Point2D
    ReDim out(0 To newLen - 1)
    Dim i As Long
    For i = 0 To addCount - 1
        out(i) = seg.pts(i)
    Next i
    For i = 0 To chainLen - 1
        out(addCount + i) = chain(i)
    Next i
    PrependSegPoints = out
End Function

Private Function PrependSegPointsRev(ByRef chain() As Point2D, ByVal chainLen As Long, _
                                     ByRef seg As Segment, ByVal skipFirst As Boolean) As Point2D()
    ' Prepend seg reversed before chain; seg.StartPt connects to chain(0)
    Dim startI As Long: startI = IIf(skipFirst, 1, 0)
    Dim addCount As Long: addCount = seg.PtCount - startI
    Dim newLen As Long: newLen = chainLen + addCount
    Dim out() As Point2D
    ReDim out(0 To newLen - 1)
    Dim i As Long
    For i = 0 To addCount - 1
        out(i) = seg.pts(seg.PtCount - 1 - i)
    Next i
    For i = 0 To chainLen - 1
        out(addCount + i) = chain(i)
    Next i
    PrependSegPointsRev = out
End Function

Private Sub CleanDuplicates(ByRef pts() As Point2D, ByVal n As Long, _
                            ByRef out() As Point2D, ByRef outLen As Long)
    ReDim out(0 To n - 1)
    Dim i As Long
    out(0) = pts(0)
    outLen = 1
    For i = 1 To n - 1
        If Not PointsAreEqual(pts(i), out(outLen - 1), CHAIN_TOL) Then
            out(outLen) = pts(i)
            outLen = outLen + 1
        End If
    Next i
End Sub

' ---- Utility ----------------------------------------------------------------

Private Function ToPoint2D(ByVal arr As Variant) As Point2D
    ToPoint2D.X = arr(0)
    ToPoint2D.Y = arr(1)
End Function

Private Function PointsAreEqual(ByRef a As Point2D, ByRef b As Point2D, ByVal tol As Double) As Boolean
    Dim dx As Double, dy As Double
    dx = a.X - b.X
    dy = a.Y - b.Y
    PointsAreEqual = (dx * dx + dy * dy) <= tol * tol
End Function

Private Function PrepareSelectionSet(ByVal doc As Object, ByVal name As String) As Object
    On Error Resume Next
    Dim ss As Object
    Set ss = doc.SelectionSets.item(name)
    If Not ss Is Nothing Then ss.Delete
    On Error GoTo 0

    Set ss = doc.SelectionSets.Add(name)
    Set PrepareSelectionSet = ss
End Function

Attribute VB_Name = "formPerfisul01"
Attribute VB_Base = "0{282FB6E9-23E7-423C-AD2E-21D46C6E0D0D}{5EFC0E17-A11D-4BF7-A45F-EA81FD515D41}"
Attribute VB_GlobalNameSpace = False
Attribute VB_Creatable = False
Attribute VB_PredeclaredId = True
Attribute VB_Exposed = False
Attribute VB_TemplateDerived = False
Attribute VB_Customizable = False







Private Sub Frame1_Click()

End Sub

Private Sub MultiPage1_Change()

End Sub

Private Sub UserForm_Initialize()
    Dim acadDoc As Object ' AcadDocument
    Dim acadLayers As Object ' AcadLayers collection
    Dim layerObj As Object ' AcadLayer
    
    On Error Resume Next
    Set acadDoc = ThisDrawing
    
    If acadDoc Is Nothing Then
        MsgBox "Could not get ThisDrawing. Make sure you are running this from BricsCAD.", vbCritical
        Exit Sub
    End If
    
    Set acadLayers = acadDoc.layers
    
    ' Clear the combo box first
    cbCamada01.Clear
    cbCamada02.Clear
    
    ' Add a default option as the first item
    cbCamada01.AddItem "-- Selecione uma camada --"
    cbCamada01.ListIndex = 0 ' Select the default option
    cbCamada02.AddItem "-- Selecione uma camada --"
    cbCamada02.ListIndex = 0 ' Select the default option
    
    ' Loop through all layers and add them to the combo box
    For Each layerObj In acadLayers
        cbCamada01.AddItem layerObj.name
        cbCamada02.AddItem layerObj.name
    Next layerObj

     cbTexto01.AddItem "CARROCERIA"
     cbTexto01.AddItem "FERRAMENTARIA"
     cbTexto01.AddItem "PORTAS"
     cbTexto01.AddItem "TAMPA"
     cbTexto01.AddItem "TETO"
     cbTexto01.AddItem "VIDROS"
    
    On Error GoTo 0
End Sub

Private Sub btnPuncionadeira_Click()
 Call ResizeAndColorCircles
 Call DetectPolygons
End Sub

Private Sub btnAddText01_Click()
    ' Check if a layer is selected
    If cbCamada01.ListIndex <= 0 Then
        MsgBox "Por favor, selecione uma camada antes de continuar.", vbExclamation, "Seleção de Camada"
        Exit Sub
    End If
    
    ' Check if text is provided
    If Trim(cbTexto01.Value) = "" Then
        MsgBox "Por favor, informe o texto a ser adicionado.", vbExclamation, "Texto não Informado"
        cbTexto01.SetFocus
        Exit Sub
    End If
    
    ' Call TextCopier_Add with the selected layer name
    Call TextCopier_Add(cbCamada01.Value)
End Sub

Private Sub btnDelText01_Click()
    ' Check if a layer is selected
    If cbCamada01.ListIndex <= 0 Then
        MsgBox "Por favor, selecione uma camada antes de continuar.", vbExclamation, "Seleção de Camada"
        Exit Sub
    End If
    
    ' Check if text is provided
    If Trim(cbTexto01.Value) = "" Then
        MsgBox "Por favor, informe o texto a ser adicionado.", vbExclamation, "Texto não Informado"
        cbTexto01.SetFocus
        Exit Sub
    End If
    
    ' Call TextCopier_Add with the selected layer name
    Call TextCopier_Del(cbCamada01.Value)
End Sub


Private Sub btnLimparCamada01_Click()
    Call LayerClean_Del(cbCamada02.Value)
End Sub


Private Sub cmdTxtList1_Click()
    Call TextSorter_IndexTexts
End Sub


Private Sub cmdListClean01_Click()
    Call LayerClean_Del("Index")
End Sub


Private Sub btnPerimetroTotal_Click()
    Call SumTotalPerimeter
End Sub


Private Sub cmdFixDouble_Click()
    Call FixDuplicatedCodes
End Sub


Private Sub btnCircleAligner_Click()
    Call CircleAligner
End Sub


Private Sub btnFixSmallGaps_Click()
    Call FixSmallGaps
End Sub


Private Sub btnHexFind_Click()
    Call DetectHexagonsAndProcessParallelLines
End Sub


Private Sub btnSimplifyContour_Click()
    Call SimplifySelectedContours
End Sub


Private Sub cmdAutoOrient_Click()
    Call AutoOrientFromForm(Me)
End Sub


Private Sub btnDetectLoops_Click()
    Call DetectOuterShapes
End Sub


Private Sub btnCellCenters_Click()
    Call DrawCellCenters
End Sub


Private Sub btnDistributeToGrid_Click()
    Call DistributeShapesToGrid
End Sub


Private Sub btnExplodeDobrasMText_Click()
    Call ExplodeMText_TexDobras
End Sub


Private Sub btnScaleToTextSize_Click()
    Call ScaleToTextSize
End Sub


Private Sub btnSheetMetalWeight_Click()
    Call CalculateSheetMetalWeight
End Sub


Private Sub btnToggleShapeExclusion_Click()
    Call ToggleShapeExclusion
End Sub

Attribute VB_Name = "zMainTest01"
Option Explicit

' ==============================================================================
' Module  : celloFingerboard.vba
' Description:
'   Draws a cello fingerboard diagram in BricsCAD ModelSpace.
'
'   The diagram contains:
'     • Four lines representing the four cello strings (C2, G2, D3, A3).
'     • Small circles marking every finger position using Equal Temperament
'       tuning distances from the nut.
'
'   Equal Temperament formula (distance from nut to semitone n):
'     d = L × ( 1 - 2^(-n/12) )
'     where L = scale length (mm), n = semitone offset above the open string.
'
'   Color modes (USE_STRING_COLORS):
'     True  ? each string has its own fixed color.
'     False ? each note name (C, C#, D … B) carries its own color class.
'
'   Sharp / flat control (DRAW_SHARPS):
'     True  ? C#, D#, F#, G#, A# positions are drawn on CELLO_Sharps layer.
'     False ? only natural notes (C, D, E, F, G, A, B) are drawn.
'
'   Layers created automatically:
'     CELLO_Strings  – the four string lines.
'     CELLO_Naturals – natural-note circles.
'     CELLO_Sharps   – sharp / flat circles (created only when DRAW_SHARPS is True).
'
'   Entry point:  DrawCelloFingerboard
' ==============================================================================


' ==============================================================================
' SECTION 1 – INSTRUMENT DIMENSIONS
' Adjust these values to match any cello size or alternate string instrument.
' ==============================================================================

Private Const SCALE_LENGTH       As Double = 685#   ' mm  Full vibrating string length (nut to bridge)
Private Const FINGERBOARD_LEN    As Double = 250#   ' mm  Visible fingerboard length to render
Private Const NUT_STRING_SPAN    As Double = 26#    ' mm  Outer-edge span of all 4 strings measured at the nut
Private Const BRIDGE_STRING_SPAN As Double = 60#    ' mm  Outer-edge span of all 4 strings measured at the bridge


' ==============================================================================
' SECTION 2 – DRAWING LAYOUT
' Controls the position and size of drawn geometry.
' ==============================================================================

Private Const ORIGIN_X           As Double = 0#     ' mm  X reference for the leftmost string at the nut
Private Const ORIGIN_Y           As Double = 0#     ' mm  Y reference for the nut line (top of diagram; bridge is below)
Private Const NOTE_RADIUS        As Double = 2.5    ' mm  Radius of each finger-position circle
Private Const NUM_SEMITONES      As Integer = 24    ' #   Semitone positions drawn per string (24 = two octaves)
Private Const STRING_WIDTH_SCALE As Double = 1#     ' ×   Multiplier applied to realistic string diameters (1.0 = true to life)
Private Const LEGEND_OFFSET_X    As Double = 50#    ' mm  Gap from the fingerboard right edge to the legend circle centre
Private Const LEGEND_ROW_SPACING As Double = 8#     ' mm  Vertical distance between legend rows (centre to centre)
Private Const LEGEND_TEXT_HEIGHT As Double = 3.5    ' mm  Note label text height


' ==============================================================================
' SECTION 3 – DISPLAY OPTIONS
' Toggle these flags to control what is drawn and how colors are applied.
' ==============================================================================

Private Const DRAW_SHARPS        As Boolean = False  ' Bool  True  = include sharp/flat (black-key) note circles
                                                    '       False = natural notes only
Private Const USE_STRING_COLORS  As Boolean = False  ' Bool  True  = color circles by string identity
                                                    '       False = color circles by note name (chromatic class)


' ==============================================================================
' SECTION 4 – LAYER NAMES
' Geometry is distributed across separate layers for easy visibility control.
' ==============================================================================

Private Const LAYER_STRINGS      As String = "CELLO_Strings"   ' String lines
Private Const LAYER_NATURALS     As String = "CELLO_Naturals"  ' Natural-note circles
Private Const LAYER_SHARPS       As String = "CELLO_Sharps"    ' Sharp/flat note circles
Private Const LAYER_LEGEND       As String = "CELLO_Legend"    ' Colour legend entities
Private Const LEGEND_TEXT_STYLE  As String = "CELLO_Arial"     ' Arial text style used by the legend


' ==============================================================================
' SECTION 5 – NOTE & STRING COLOURS
' RGB Long values initialised by InitNoteColors at runtime.
' Edit only this block to remap any colour; no other code needs to change.
' ==============================================================================

Private lngNoteC   As Long   ' C  – Crimson red
Private lngNoteCsh As Long   ' C# – Dark orange
Private lngNoteD   As Long   ' D  – Orange
Private lngNoteDsh As Long   ' D# – Yellow-green
Private lngNoteE   As Long   ' E  – Gold yellow
Private lngNoteF   As Long   ' F  – Green
Private lngNoteFsh As Long   ' F# – Dark green
Private lngNoteG   As Long   ' G  – Cyan
Private lngNoteGsh As Long   ' G# – Steel blue
Private lngNoteA   As Long   ' A  – Medium blue
Private lngNoteAsh As Long   ' A# – Magenta
Private lngNoteB   As Long   ' B  – Violet


' ==============================================================================
' PUBLIC ENTRY POINT
' ==============================================================================

' DrawCelloFingerboard
' --------------------
' Main macro entry point. Call this from the BricsCAD Macro dialog or a toolbar button.
'
' Workflow:
'   1. Ensure all drawing layers exist.
'   2. Draw the four cello string lines (C2, G2, D3, A3).
'   3. Plot finger-position circles for every requested semitone on each string.
'   4. Regen the viewports.
Public Sub DrawCelloFingerboard()

    Dim doc As AcadDocument
    Set doc = ThisDrawing

    ' --- Step 0: Initialise all note and string RGB colours ---
    Call InitNoteColors

    ' --- Step 1: Ensure required layers exist ---
    Call EnsureLayer(doc, LAYER_STRINGS, acWhite)
    Call EnsureLayer(doc, LAYER_NATURALS, acWhite)
    If DRAW_SHARPS Then
        Call EnsureLayer(doc, LAYER_SHARPS, acWhite)
    End If
    Call EnsureLayer(doc, LAYER_LEGEND, acWhite)
    Call EnsureTextStyle(doc, LEGEND_TEXT_STYLE, "arial.ttf")

    ' --- Step 2: Draw the four string lines (indices 0=C, 1=G, 2=D, 3=A) ---
    Dim s As Integer
    For s = 0 To 3
        Call DrawStringLine(doc, s)
    Next s

    ' --- Step 3: Draw finger-position circles on each string ---
    For s = 0 To 3
        Call DrawNoteCircles(doc, s)
    Next s

    ' --- Step 4: Draw colour / note legend ---
    Call DrawColorLegend(doc)

    ' --- Step 5: Refresh all viewports ---
    doc.Regen acAllViewports

    ' Summary message
    Dim msg As String
    msg = "Cello fingerboard diagram drawn successfully." & vbCrLf & vbCrLf
    msg = msg & "  Scale length      : " & SCALE_LENGTH & " mm" & vbCrLf
    msg = msg & "  Fingerboard length: " & FINGERBOARD_LEN & " mm" & vbCrLf
    msg = msg & "  Semitones drawn   : " & NUM_SEMITONES & " per string" & vbCrLf
    msg = msg & "  Sharps drawn      : " & IIf(DRAW_SHARPS, "Yes", "No") & vbCrLf
    msg = msg & "  Color mode        : " & IIf(USE_STRING_COLORS, "By string", "By note name")
    MsgBox msg, vbInformation, "DrawCelloFingerboard"

End Sub


' ==============================================================================
' DRAWING – STRING LINES
' ==============================================================================

' StringBaseWidthMM
' -----------------
' Returns the realistic physical diameter (mm) of each cello string.
' Values are typical wound-steel/gut-core gauges for a full-size cello.
' Multiply by STRING_WIDTH_SCALE for fine-tuning.
'
'   stringIndex : 0 = C2  1 = G2  2 = D3  3 = A3
Private Function StringBaseWidthMM(stringIndex As Integer) As Double
    Select Case stringIndex
        Case 0: StringBaseWidthMM = 1.1    ' C2 – thickest wound string
        Case 1: StringBaseWidthMM = 0.9    ' G2
        Case 2: StringBaseWidthMM = 0.7    ' D3
        Case 3: StringBaseWidthMM = 0.55   ' A3 – thinnest string
        Case Else: StringBaseWidthMM = 0.5
    End Select
End Function


' NearestLineweight
' -----------------
' Snaps a desired lineweight in mm to the nearest value supported by
' AutoCAD / BricsCAD (which only accept a fixed set of integer weights
' expressed in hundredths of a millimetre).
'
'   widthMM : desired lineweight in millimetres
Private Function NearestLineweight(widthMM As Double) As Long

    ' All valid ACI lineweight values in 1/100 mm units
    Dim lw(23) As Long
    lw(0) = 0:    lw(1) = 5:    lw(2) = 9:    lw(3) = 13
    lw(4) = 15:   lw(5) = 18:   lw(6) = 20:   lw(7) = 25
    lw(8) = 30:   lw(9) = 35:   lw(10) = 40:  lw(11) = 50
    lw(12) = 53:  lw(13) = 60:  lw(14) = 70:  lw(15) = 80
    lw(16) = 90:  lw(17) = 100: lw(18) = 106: lw(19) = 120
    lw(20) = 140: lw(21) = 158: lw(22) = 200: lw(23) = 211

    Dim target As Long
    target = CLng(widthMM * 100#)

    Dim best As Long
    Dim bestDiff As Long
    best = lw(0)
    bestDiff = Abs(target - lw(0))

    Dim i As Integer
    For i = 1 To 23
        Dim d As Long
        d = Abs(target - lw(i))
        If d < bestDiff Then
            bestDiff = d
            best = lw(i)
        End If
    Next i

    NearestLineweight = best
End Function


' DrawStringLine
' --------------
' Draws one of the four cello strings as a straight line from the nut to the
' end of the visible fingerboard. The string X-coordinate is interpolated
' between the nut span and the bridge span to reflect the natural taper.
'
'   doc         : active AcadDocument object
'   stringIndex : 0 = C2 (lowest/widest)  1 = G2  2 = D3  3 = A3 (highest)
Private Sub DrawStringLine(doc As AcadDocument, stringIndex As Integer)

    ' Resolve the open-string chromatic root so the line color matches its open note
    Dim openChromatic As Integer
    Select Case stringIndex
        Case 0: openChromatic = 0   ' C
        Case 1: openChromatic = 7   ' G
        Case 2: openChromatic = 2   ' D
        Case 3: openChromatic = 9   ' A
    End Select

    ' Start point at the nut (Y = ORIGIN_Y, top of diagram)
    Dim StartPt(2) As Double
    StartPt(0) = StringXAtY(stringIndex, 0#)
    StartPt(1) = ORIGIN_Y
    StartPt(2) = 0#

    ' End point at the far end of the visible fingerboard (below the nut)
    Dim EndPt(2) As Double
    EndPt(0) = StringXAtY(stringIndex, FINGERBOARD_LEN)
    EndPt(1) = ORIGIN_Y - FINGERBOARD_LEN
    EndPt(2) = 0#

    Dim lineObj As AcadLine
    Set lineObj = doc.modelSpace.AddLine(StartPt, EndPt)
    lineObj.layer = LAYER_STRINGS
    ' Use the same color dispatcher as note circles so lines always match
    Call SetEntityRGB(lineObj, CircleColor(stringIndex, openChromatic))
    ' Apply realistic string diameter scaled by STRING_WIDTH_SCALE
    lineObj.Lineweight = NearestLineweight(StringBaseWidthMM(stringIndex) * STRING_WIDTH_SCALE)

End Sub


' ==============================================================================
' DRAWING – FINGER-POSITION CIRCLES
' ==============================================================================

' DrawNoteCircles
' ---------------
' Iterates through all requested semitone positions on a given string and places
' a circle at each one. The Y-position of each circle is calculated with the
' Equal Temperament formula. Sharp notes are drawn only when DRAW_SHARPS = True.
' Positions beyond FINGERBOARD_LEN are silently skipped.
'
'   doc         : active AcadDocument object
'   stringIndex : 0 = C2  1 = G2  2 = D3  3 = A3
Private Sub DrawNoteCircles(doc As AcadDocument, stringIndex As Integer)

    ' Open-string chromatic root (0=C … 11=B) and MIDI base note for octave labels
    Dim openChromatic As Integer    ' position within a chromatic octave (mod 12)
    Dim midiBase      As Integer    ' MIDI note number of the open string

    Select Case stringIndex
        Case 0: openChromatic = 0:  midiBase = 36  ' C2  (MIDI 36)
        Case 1: openChromatic = 7:  midiBase = 43  ' G2  (MIDI 43)
        Case 2: openChromatic = 2:  midiBase = 50  ' D3  (MIDI 50)
        Case 3: openChromatic = 9:  midiBase = 57  ' A3  (MIDI 57)
    End Select

    Dim n As Integer
    For n = 1 To NUM_SEMITONES      ' n=0 is the open string (nut); start at 1

        ' Absolute chromatic index for this note (may exceed 11; use mod 12 for note name)
        Dim absChromatic As Integer
        absChromatic = openChromatic + n

        ' Determine whether this semitone is a sharp / flat position
        Dim sharp As Boolean
        sharp = IsSharpNote(absChromatic)

        ' Conditionally skip sharp/flat positions based on the DRAW_SHARPS flag
        If Not (sharp And Not DRAW_SHARPS) Then

            ' --- Equal Temperament: distance from nut to this semitone ---
            Dim distFromNut As Double
            distFromNut = NoteDistanceFromNut(SCALE_LENGTH, n)

            ' Skip positions that fall beyond the drawable fingerboard length
            If distFromNut <= FINGERBOARD_LEN Then

                ' Compute the XY centre of the circle
                ' Y decreases downward from the nut (mirrored layout)
                Dim cx As Double
                Dim cy As Double
                cx = StringXAtY(stringIndex, distFromNut)
                cy = ORIGIN_Y - distFromNut

                ' Choose layer (natural vs. sharp) and color
                Dim lyr As String
                lyr = IIf(sharp, LAYER_SHARPS, LAYER_NATURALS)

                Dim col As Long
                col = CircleColor(stringIndex, absChromatic)

                ' Draw the finger-position circle
                Call DrawNoteCircle(doc, cx, cy, col, lyr)

            End If
        End If

    Next n

End Sub


' DrawNoteCircle
' --------------
' Places a single circle in ModelSpace at the given centre coordinates.
'
'   doc     : active AcadDocument object
'   x, y    : centre of the circle in mm
'   col     : AutoCAD Color Index (ACI) to apply to the entity
'   lyrName : target layer name
Private Sub DrawNoteCircle(doc As AcadDocument, _
                           X As Double, Y As Double, _
                           col As Long, lyrName As String)
    Dim center(2) As Double
    center(0) = X
    center(1) = Y
    center(2) = 0#

    Dim circObj As AcadCircle
    Set circObj = doc.modelSpace.AddCircle(center, NOTE_RADIUS)
    circObj.layer = lyrName
    Call SetEntityRGB(circObj, col)

    ' Fill the circle with a solid hatch in the same color
    Dim hatchObj As AcadHatch
    Set hatchObj = doc.modelSpace.AddHatch(acHatchPatternTypePreDefined, "SOLID", True)
    hatchObj.layer = lyrName
    Call SetEntityRGB(hatchObj, col)
    Dim boundary(0) As AcadEntity
    Set boundary(0) = circObj
    hatchObj.AppendOuterLoop boundary
    hatchObj.Evaluate

End Sub


' ==============================================================================
' GEOMETRY HELPERS
' ==============================================================================

' StringXAtY
' ----------
' Returns the X coordinate of a given string at a distance y from the nut.
' The fingerboard tapers from NUT_STRING_SPAN at the nut to BRIDGE_STRING_SPAN
' at the bridge. Both spans are centred around the same X midpoint, so the
' taper is symmetrical. Linear interpolation is used along the full SCALE_LENGTH.
'
'   stringIndex : 0 = C (leftmost)  1 = G  2 = D  3 = A (rightmost)
'   y           : distance in mm from the nut
Private Function StringXAtY(stringIndex As Integer, Y As Double) As Double

    ' Horizontal centre reference (ensures symmetric taper)
    Dim nutCenter As Double
    nutCenter = ORIGIN_X + NUT_STRING_SPAN / 2#

    ' X of this string at the nut end and at the bridge end
    Dim xNut    As Double
    Dim xBridge As Double
    xNut = nutCenter - NUT_STRING_SPAN / 2# + CDbl(stringIndex) * (NUT_STRING_SPAN / 3#)
    xBridge = nutCenter - BRIDGE_STRING_SPAN / 2# + CDbl(stringIndex) * (BRIDGE_STRING_SPAN / 3#)

    ' Linear interpolation: t=0 at nut, t=1 at bridge
    Dim t As Double
    t = Y / SCALE_LENGTH

    StringXAtY = xNut + (xBridge - xNut) * t

End Function


' NoteDistanceFromNut
' -------------------
' Returns the distance in mm from the nut to the given semitone position,
' using the standard Equal Temperament formula:
'
'   d = L × ( 1 - 2^(-n/12) )
'
' where L is the scale length in mm and n is the semitone offset from the
' open string. Returns 0 for n = 0 (open string / nut position).
'
'   scaleLength : vibrating string length in mm (e.g. 690 for a full-size cello)
'   semitone    : integer offset above the open string (1 = first semitone)
Private Function NoteDistanceFromNut(scaleLength As Double, semitone As Integer) As Double

    If semitone <= 0 Then
        NoteDistanceFromNut = 0#
        Exit Function
    End If

    ' Core Equal Temperament formula
    NoteDistanceFromNut = scaleLength * (1# - (1# / (2# ^ (CDbl(semitone) / 12#))))

End Function


' IsSharpNote
' -----------
' Returns True when the given absolute chromatic index resolves to a sharp
' or flat note within an octave.
'
' Sharp positions within a chromatic octave (mod 12):
'   1 = C#/Db   3 = D#/Eb   6 = F#/Gb   8 = G#/Ab   10 = A#/Bb
'
'   chromaticIndex : any integer; only its mod-12 value is examined
Private Function IsSharpNote(chromaticIndex As Integer) As Boolean

    Select Case ((chromaticIndex Mod 12) + 12) Mod 12
        Case 1, 3, 6, 8, 10
            IsSharpNote = True
        Case Else
            IsSharpNote = False
    End Select

End Function


' NoteName
' --------
' Returns the note name string (e.g. "C", "C#", "D") for any absolute
' chromatic index, using sharp spelling for accidentals.
'
'   absoluteChromatic : any integer; only its mod-12 value is used
Private Function NoteName(absoluteChromatic As Integer) As String

    Dim names(11) As String
    names(0) = "C":  names(1) = "C#": names(2) = "D":    names(3) = "D#"
    names(4) = "E":  names(5) = "F":   names(6) = "F#": names(7) = "G"
    names(8) = "G#": names(9) = "A":   names(10) = "A#": names(11) = "B"

    NoteName = names(((absoluteChromatic Mod 12) + 12) Mod 12)

End Function


' ==============================================================================
' COLOUR HELPERS
' ==============================================================================

' StringColor
' -----------
' Returns a distinct AutoCAD Color Index (ACI) for each cello string.
' The same colors are applied to string lines and, when USE_STRING_COLORS
' is True, to note circles.
'
'   stringIndex : 0 = C  1 = G  2 = D  3 = A
Private Function StringColor(stringIndex As Integer) As Long

    ' Each string's color matches its open-note color (C=0, G=7, D=2, A=9)
    Select Case stringIndex
        Case 0: StringColor = NoteColor(0)   ' C string ? C note color
        Case 1: StringColor = NoteColor(7)   ' G string ? G note color
        Case 2: StringColor = NoteColor(2)   ' D string ? D note color
        Case 3: StringColor = NoteColor(9)   ' A string ? A note color
        Case Else: StringColor = RGB(255, 255, 255)
    End Select

End Function


' NoteColor
' ---------
' Returns a visually distinct AutoCAD Color Index (ACI) for each of the 12
' chromatic note classes. Colors are consistent across all strings and octaves,
' so the same note name always appears in the same color.
'
'   chromaticIndex : any integer; only its mod-12 value is used
Private Function NoteColor(chromaticIndex As Integer) As Long

    Select Case ((chromaticIndex Mod 12) + 12) Mod 12
        Case 0:  NoteColor = lngNoteC
        Case 1:  NoteColor = lngNoteCsh
        Case 2:  NoteColor = lngNoteD
        Case 3:  NoteColor = lngNoteDsh
        Case 4:  NoteColor = lngNoteE
        Case 5:  NoteColor = lngNoteF
        Case 6:  NoteColor = lngNoteFsh
        Case 7:  NoteColor = lngNoteG
        Case 8:  NoteColor = lngNoteGsh
        Case 9:  NoteColor = lngNoteA
        Case 10: NoteColor = lngNoteAsh
        Case 11: NoteColor = lngNoteB
        Case Else: NoteColor = RGB(255, 255, 255)
    End Select

End Function


' CircleColor
' -----------
' Dispatches to the appropriate color function based on the USE_STRING_COLORS flag.
'
'   USE_STRING_COLORS = True  ? delegates to StringColor(stringIndex)
'   USE_STRING_COLORS = False ? delegates to NoteColor(absoluteChromatic)
'
'   stringIndex      : 0–3 (string identity)
'   absoluteChromatic: open-string root + semitone offset (used for note-class color)
Private Function CircleColor(stringIndex As Integer, absoluteChromatic As Integer) As Long

    If USE_STRING_COLORS Then
        CircleColor = StringColor(stringIndex)
    Else
        CircleColor = NoteColor(absoluteChromatic)
    End If

End Function


' ==============================================================================
' LEGEND
' ==============================================================================

' NoteNamePT
' ----------
' Returns the note name in Brazilian Portuguese solfège notation.
' Accidentals are spelled with a sharp sign (#).
'
'   chromaticIndex : any integer; only its mod-12 value is used
Private Function NoteNamePT(chromaticIndex As Integer) As String
    Dim names(11) As String
    names(0) = "D" & Chr(243)               ' Dó
    names(1) = "D" & Chr(243) & "#"         ' Dó#
    names(2) = "R" & Chr(233)               ' Ré
    names(3) = "R" & Chr(233) & "#"         ' Ré#
    names(4) = "Mi"                         ' Mi
    names(5) = "F" & Chr(225)               ' Fá
    names(6) = "F" & Chr(225) & "#"         ' Fá#
    names(7) = "Sol"                        ' Sol
    names(8) = "Sol#"                       ' Sol#
    names(9) = "L" & Chr(225)               ' Lá
    names(10) = "L" & Chr(225) & "#"        ' Lá#
    names(11) = "Si"                        ' Si
    NoteNamePT = names(((chromaticIndex Mod 12) + 12) Mod 12)
End Function


' DrawColorLegend
' ---------------
' Draws a colour/note legend to the right of the fingerboard. The origin of
' the legend is LEGEND_OFFSET_X mm past the widest (bridge) edge of the diagram.
' Each row contains:
'   • A filled circle (same size and ACI colour as the fingerboard note circles)
'   • The note name in Brazilian Portuguese (LEGEND_TEXT_STYLE, LEGEND_TEXT_HEIGHT, black)
'
' Only notes that appear on the fingerboard are listed: sharps are included
' only when DRAW_SHARPS is True.
Private Sub DrawColorLegend(doc As AcadDocument)

    ' X centre of the legend circles: rightmost bridge-span edge + offset
    Dim legendX As Double
    legendX = ORIGIN_X + (NUT_STRING_SPAN + BRIDGE_STRING_SPAN) / 2# + LEGEND_OFFSET_X

    Dim row     As Integer
    Dim c       As Integer
    row = 0

    For c = 0 To 11
        If Not (IsSharpNote(c) And Not DRAW_SHARPS) Then

            Dim cy As Double
            cy = ORIGIN_Y - CDbl(row) * LEGEND_ROW_SPACING

            Dim col As Long
            col = NoteColor(c)

            ' Filled circle – identical appearance to fingerboard note circles
            Call DrawNoteCircle(doc, legendX, cy, col, LAYER_LEGEND)

            ' Note label to the right of the circle
            Dim insertPt(2) As Double
            insertPt(0) = legendX + NOTE_RADIUS + 2#
            insertPt(1) = cy - LEGEND_TEXT_HEIGHT / 2#
            insertPt(2) = 0#

            Dim txtObj As AcadText
            Set txtObj = doc.modelSpace.AddText(NoteNamePT(c), insertPt, LEGEND_TEXT_HEIGHT)
            txtObj.layer = LAYER_LEGEND
            txtObj.Color = acWhite              ' ACI 7: renders black on white paper
            txtObj.styleName = LEGEND_TEXT_STYLE

            row = row + 1
        End If
    Next c

End Sub


' ==============================================================================
' UTILITY
' ==============================================================================

' InitNoteColors
' --------------
' Assigns RGB values to all module-level note and string colour variables.
' Called once at the start of DrawCelloFingerboard.
' Edit the RGB() calls below to remap colours; nothing else needs to change.
Private Sub InitNoteColors()
    lngNoteC = RGB(220, 20, 60)       ' C  – Crimson red
    lngNoteCsh = RGB(180, 60, 0)      ' C# – Dark orange
    lngNoteD = RGB(255, 140, 0)       ' D  – Orange
    lngNoteDsh = RGB(154, 205, 50)    ' D# – Yellow-green
    lngNoteE = RGB(255, 215, 0)       ' E  – Gold yellow
    lngNoteF = RGB(0, 180, 0)         ' F  – Green
    lngNoteFsh = RGB(0, 100, 0)       ' F# – Dark green
    lngNoteG = RGB(0, 140, 210)       ' G  – Cyan/Light blue
    lngNoteGsh = RGB(70, 130, 180)    ' G# – Steel blue
    lngNoteA = RGB(0, 0, 205)         ' A  – Medium blue
    lngNoteAsh = RGB(200, 0, 200)     ' A# – Magenta
    lngNoteB = RGB(138, 43, 226)      ' B  – Violet

End Sub


' SetEntityRGB
' ------------
' Sets the TrueColor property of any AcadEntity from a VBA RGB Long value,
' giving 24-bit colour instead of the 256-entry ACI palette.
'
'   ent      : the entity to colour
'   rgbColor : a Long produced by VBA's RGB() function
Private Sub SetEntityRGB(ent As AcadEntity, rgbColor As Long)
    Dim r As Long
    Dim g As Long
    Dim b As Long
    r = rgbColor And 255&
    g = (rgbColor \ 256&) And 255&
    b = (rgbColor \ 65536) And 255&
    Dim oCol As AcadAcCmColor
    Set oCol = ent.TrueColor
    oCol.SetRGB CInt(r), CInt(g), CInt(b)
    ent.TrueColor = oCol
End Sub


' EnsureLayer
' -----------
' Creates a layer with the given name and default color if it does not already
' exist. Leaves any existing layer with that name unchanged.
'
'   doc     : active AcadDocument object
'   lyrName : name of the layer to create / verify
'   col     : default AutoCAD Color Index applied only when the layer is created
Private Sub EnsureLayer(doc As AcadDocument, lyrName As String, col As Long)

    Dim lyr As AcadLayer
    On Error Resume Next
    Set lyr = doc.layers.item(lyrName)
    If Err.Number <> 0 Then
        Err.Clear
        Set lyr = doc.layers.Add(lyrName)
        lyr.Color = col
    End If
    On Error GoTo 0

End Sub


' EnsureTextStyle
' ---------------
' Creates a text style with the given name and TrueType font file if it does
' not already exist. Leaves any existing style with that name unchanged.
'
'   doc       : active AcadDocument object
'   styleName : name of the text style to create / verify
'   fontFile  : TrueType font filename (e.g. "arial.ttf")
Private Sub EnsureTextStyle(doc As AcadDocument, styleName As String, fontFile As String)

    Dim sty As AcadTextStyle
    On Error Resume Next
    Set sty = doc.TextStyles.item(styleName)
    If Err.Number <> 0 Then
        Err.Clear
        Set sty = doc.TextStyles.Add(styleName)
        sty.fontFile = fontFile
    End If
    On Error GoTo 0

End Sub
